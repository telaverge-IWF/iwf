--------------------------------------------------------------------------------
--                                                                            --
--      Copyright 2000 IntelliNet Technologies, Inc. All Rights Reserved.     --
--              Manufactured in the United States of America.                 --
--        1990 W. New Haven Ste. 312, Melbourne, Florida, 32904 U.S.A.        --
--                                                                            --
--    This product and related documentation is protected by copyright and    --
--    distributed under licenses restricting its use, copying, distribution   --
--    and decompilation.  No part of this product or related documentation    --
--    may be reproduced in any form by any means without prior written        --
--    authorization of IntelliNet Technologies and its licensors, if any.     --
--                                                                            --
--    RESTRICTED RIGHTS LEGEND:  Use, duplication, or disclosure by the       --
--    government is subject to restrictions as set forth in subparagraph      --
--    (c)(1)(ii) of the Rights in Technical Data and Computer Software        --
--    clause at DFARS 252.227-7013 and FAR 52.227-19.                         --
--                                                                            --
--------------------------------------------------------------------------------
--                                                                            --
--  CONTRACT: INTERNAL                                                        --
--                                                                            --
--------------------------------------------------------------------------------
--
--  ID: $Id: cap_v4_lrf.asn,v 9.1 2005/03/23 12:51:13 cvsadmin Exp $
--
--------------------------------------------------------------------------------

--------------------------------------------------------------------------------
--------------------------------------------------------------------------------
--
--  ASN.1 Module for CAMEL CAP Version 4 (CAP V4).
--
--  LRF (Local Reference Format) version (from specification).
--
--------------------------------------------------------------------------------
--------------------------------------------------------------------------------

--
--  Specification identification:
--
--      ETSI TS 129 078 V5.5.0 (2002-06) (from file ts_129078v050000p.pdf).
--
--      Digital cellular telecommunications system (Phase 2+) (GSM)
--      Universal Mobile Telecommunications System (UMTS);
--      Customised Applications for Mobile network Enhanced Logic (CAMEL)
--      CAMEL Application Part (CAP) specification
--      (3G TS 29.078 version 5.5.0 Release 2002)
--
--

--
--  Modules currently not generated (and therefore commented out with the 
--  comment prefix '-''-'"not impl "):
--
--  o   CAP-operationcodes - contains operation code values that are 
--      hand-written, not generated.
--
--
--  o   CAP-errorcodes - contains operation code values that are hand-written,
--      not generated.
-- 
--
--  o   CAP-classes - contains classes that are not yet supported by compiler.
--      Usually ANY is used as a substitute. Note that the object named
--      networkSpecificBoundSet of class PARAMETERS-BOUND is replaced by a list
--      of INTEGER values.
-- 
--  o   CAP-object-identifiers - contains Object Identifier values that are 
--      hand-written.
--
--  o   CAP-gsmSSF-gsmSCF-pkgs-contracts-acs - contains contracs, packages and
--      ACs.
--
--  o   CAP-gsmSCF-gsmSRF-pkgs-contracts-acs - contains contracts, packages and
--      ACs.
--
--  o   CAP-smsSSF-gsmSCF-pkgs-contracts-acs - contains contracts, packages and
--      ACs.
--  
--  o   CAP-gprsSSF-gsmSCF-pkgs-contracts-acs - contains contracts, packages and
--      ACs.
-- 

--
--  Only one module (named CAP-V3) is used. All information related to modules
--  import and export is commented out with the comment prefix '-''-'
--  "not used ".
--

--
--  The EXTENSION class is not used. The ExtensionField type has been modified
--  modified to use a type ANY. Should be similar for the encoding/decoding.
--  Original type and class definitions commented out with the comment prefix
--  '-''-'"change for compiler " or '-''-'"not impl ".
--

--
--  The PARAMETERS-BOUND class and the object networkSpecificBoundSet are not
--  used. Original type and class definitions are commented out with the comment
--  prefix '-''-'"not impl ". A list of INTEGER values is used instead.
--

--
--	All bound.&xxxxxx are partially commented out (replaced by ' ''-'-' bound.& 
--  '-''-'' 'xxxxxx). All the "xxxxxx" are defined as INTEGER value references.
--

--
--	All the {PARAMETERS-BOUND : bound} parameter lists are commented out 
--  (replaced by ' ''-''-' {PARAMETERS-BOUND: bound} '-''-'' ').
--

--
--	All the {bound} parameters are commented out (replaced by ' ''-''-' {bound}
--  '-''-'' '
--

--
--	Two typos have been corrected in PDPType. The name of named type (part of a
--  SEQUENCE component list) must be an identifier (ASN.1 recommendations) and 
--  therefore must start by a lower-case letter. "PDPTypeOrganization" has been
--  replaced by "pDPTypeOrganization". "PDPTypeNumber" has been replaced by 
--  "pDPTypeNumber".
--

-- 
--  Few typos have been corrected in UnavailableNetworkResource. The name of a 
--  named number (part of an ENUMERATED enumeration) must be an identifier
--  (ASN.1 recommendations) and therefore must start by a lower-case letter.
--  All the name have been modified to start by a lower-case letter.
-- 

--
--	The named type name "gPRSEvent" in type RequestReportGPRSEventArg has been
--  replaced by "gPRSEvents" to avoid a (rare) name collision issue with AsnCC
--  V2 compiler (not significant). Actually more meaningful.
--

--
-- Imported from GSMMAP V6
-- IMEI
-- TBCD-STRING
-- SupportedCamelPhases
--
--
-- Imported from GSMMAP V8
-- RAIdentity 
-- GPRSMSClass
-- MSNetworkCapability                       
-- MSRadioAccessCapability 
-- MS-Classmark2
-- SupportedCamel4Subsets
--
--
--  The following ASN.1 types have been added (copied from their respective
--  ASN.1 modules, see import clauses of CAP-dataTypes).
--------------------------------------------------------------------------------
--------------------------------------------------------------------------------
-- Added global module definition (begin).
--------------------------------------------------------------------------------
--------------------------------------------------------------------------------

CAP-V4

DEFINITIONS

IMPLICIT TAGS

::=

BEGIN

--------------------------------------------------------------------------------
--------------------------------------------------------------------------------


-- Module ----------------------------------------------------------------------
--------------------------------------------------------------------------------
-- CAP Common Data Types.
--------------------------------------------------------------------------------
--------------------------------------------------------------------------------


------------------------------------------------------------
------------------------------------------------------------
-- Added ASN.1 types.
------------------------------------------------------------
------------------------------------------------------------

------------------------------------------------------------
-- IN ITU CS1 types.
------------------------------------------------------------
-- 
-- CallingPartysCategory,
-- HighLayerCompatibility,
-- Integer4,
-- LegID,
-- RedirectionInformation,
-- ServiceKey
--  Duration,
--  Interval
	

Duration ::= INTEGER (-2..86400)

Interval ::= INTEGER (-1..60000)

CallingPartysCategory ::= OCTET STRING (SIZE(1))

HighLayerCompatibility ::= OCTET STRING (SIZE (highLayerCompatibilityLength))

highLayerCompatibilityLength INTEGER ::= 2

Integer4 ::= INTEGER (0..2147483647)

LegID ::= CHOICE {
    sendingSideID   [0] LegType,
    receivingSideID [1] LegType
    }

RedirectionInformation ::= OCTET STRING (SIZE(2))

ServiceKey ::= INTEGER (0..2147483647)

------------------------------------------------------------
-- IN ITU CS2 types.
------------------------------------------------------------
--
--
-- BothwayThroughConnectionInd
-- CriticalityType
-- MiscCallInfo
-- Duration
-- Interval
-- CallSegmentID 

CallSegmentID  --{PARAMETERS-BOUND : bound}-- ::= INTEGER (1..numOfCSs)

BothwayThroughConnectionInd ::= ENUMERATED {
    bothwayPathRequired(0),
    bothwayPathNotRequired(1)
    }

CriticalityType ::= ENUMERATED {
        ignore(0),
        abort(1)
        } 

MiscCallInfo ::= SEQUENCE {
    messageType [0] ENUMERATED {
             request(0),
             notification(1)
             },
dpAssignment    [1] ENUMERATED {
             individualLine(0),
             groupBased(1),
             officeBased(2)
             }  OPTIONAL
    }

--Duration ::= INTEGER (-2..86400)

--Interval ::= INTEGER (-1..60000)

numOfCSs		INTEGER ::= 10

------------------------------------------------------------
-- MAP V6 (3G) types. 
------------------------------------------------------------
-- 
--
-- IMSI,
-- ISDN-AddressString,
-- Ext-BasicServiceCode,
-- NAEA-CIC
-- Ext-QoS-Subscribed,
-- GeographicalInformation,
-- GSN-Address,
-- LocationInformation,
-- LSAIdentity,
-- QoS-Subscribed,
-- SubscriberState
-- CallReferenceNumber,
-- SuppressionOfAnnouncement
-- ExtensionContainer


Ext-QoS-Subscribed ::= OCTET STRING (SIZE (1..9))

GSN-Address ::= OCTET STRING (SIZE (5..17))

QoS-Subscribed ::= OCTET STRING (SIZE (3))
    -- Octets are coded according to TS GSM 04.08.




IMSI ::= OCTET STRING (SIZE (3..8))

ISDN-AddressString ::= OCTET STRING (SIZE (1..maxISDN-AddressLength))
maxISDN-AddressLength  INTEGER ::= 9

Ext-BasicServiceCode ::= CHOICE {
    ext-BearerService   [2] Ext-BearerServiceCode,
    ext-Teleservice [3] Ext-TeleserviceCode}

Ext-BearerServiceCode ::= OCTET STRING (SIZE (1..5))

Ext-TeleserviceCode ::= OCTET STRING (SIZE (1..5))

NAEA-CIC ::= OCTET STRING (SIZE (3))

LocationInformation ::= SEQUENCE {
    ageOfLocationInformation                AgeOfLocationInformation            OPTIONAL,
    geographicalInformation             [0] GeographicalInformation             OPTIONAL,
    vlr-number                          [1] ISDN-AddressString                  OPTIONAL,
    locationNumber                      [2] LocationNumber                      OPTIONAL,
    cellGlobalIdOrServiceAreaIdOrLAI    [3] CellGlobalIdOrServiceAreaIdOrLAI    OPTIONAL,
    extensionContainer                  [4] ExtensionContainer                  OPTIONAL,
    ... ,
    selectedLSA-Id                      [5] LSAIdentity                         OPTIONAL,
    msc-Number                          [6] ISDN-AddressString                  OPTIONAL,
    geodeticInformation                 [7] GeodeticInformation                 OPTIONAL, 
    currentLocationRetrieved            [8] NULL                                OPTIONAL }


AgeOfLocationInformation ::= INTEGER (0..32767)

GeographicalInformation ::= OCTET STRING (SIZE (8))

CellGlobalIdOrServiceAreaIdOrLAI ::= CHOICE {
    cellGlobalIdOrServiceAreaIdFixedLength  [0] CellGlobalIdOrServiceAreaIdFixedLength,
    laiFixedLength                          [1] LAIFixedLength}

CellGlobalIdOrServiceAreaIdFixedLength ::= OCTET STRING (SIZE (7))

LAIFixedLength ::= OCTET STRING (SIZE (5))

--change for compiler MAP-EXTENSION  ::= CLASS {
--change for compiler 	&ExtensionType				OPTIONAL,
--change for compiler 	&extensionId 	OBJECT IDENTIFIER }
	-- The length of the Object Identifier shall not exceed 16 octets and the
	-- number of components of the Object Identifier shall not exceed 16

-- data types

ExtensionContainer ::= SEQUENCE {
	privateExtensionList	[0]PrivateExtensionList	OPTIONAL, 
	pcs-Extensions	[1]PCS-Extensions	OPTIONAL,
	...}

PrivateExtensionList ::= SEQUENCE SIZE (1..maxNumOfPrivateExtensions) OF
				PrivateExtension

--change for compiler PrivateExtension ::= SEQUENCE {
--change for compiler 	extId		MAP-EXTENSION.&extensionId
--change for compiler 				({ExtensionSet}),
--change for compiler 	extType		MAP-EXTENSION.&ExtensionType
--change for compiler 				({ExtensionSet}{@extId})	OPTIONAL}

------------------------------------------------------------
-- Replacement for type PrivateExtension.
------------------------------------------------------------

PrivateExtension ::= SEQUENCE {
    extId			OBJECT IDENTIFIER,
    extType			ANY
    }

maxNumOfPrivateExtensions  INTEGER ::= 10

--change for compiler ExtensionSet		MAP-EXTENSION ::=
--change for compiler 		{...
		 -- ExtensionSet is the set of all defined private extensions
--change for compiler 	}

	-- Unsupported private extensions shall be discarded if received.


PCS-Extensions ::= SEQUENCE {
	...}

LSAIdentity ::= OCTET STRING (SIZE (3))

GeodeticInformation ::= OCTET STRING (SIZE (10))

SubscriberState ::= CHOICE {
	assumedIdle	[0] NULL,
	camelBusy	[1] NULL,
	netDetNotReachable	NotReachableReason,
	notProvidedFromVLR	[2] NULL}

NotReachableReason ::= ENUMERATED {
	msPurged (0),
	imsiDetached (1),
	restrictedArea (2),
	notRegistered (3)}

CUG-Index ::= INTEGER (0..32767)

CUG-Interlock ::= OCTET STRING (SIZE (4))

CallReferenceNumber ::= OCTET STRING (SIZE (1..8))

SuppressionOfAnnouncement ::= NULL


--ExtensionContainer ::= SEQUENCE {
--    privateExtensionList    [0]PrivateExtensionList OPTIONAL, 
--   pcs-Extensions  [1]PCS-Extensions   OPTIONAL,
--    ...}


------------------------------------------------------------
-- TCAPMessages types (from TCAPMessages).
------------------------------------------------------------
-- 
-- TCInvokeIdSet
--

TCInvokeIdSet ::= INTEGER (-128..127)


	
AccessPointName  -- {PARAMETERS-BOUND: bound} -- ::= OCTET STRING (SIZE(
            -- bound.& -- minAccessPointNameLength ..
            -- bound.& -- maxAccessPointNameLength))
-- Indicates the AccessPointName, refer to 3GPP TS 24.008 [9] for the encoding.
-- It shall be coded as in the value part defined in 3GPP TS 24.008,
-- i.e. the 3GPP TS 24.008 IEI and 3GPP TS 24.008 octet length indicator
-- shall not be included.


AChBillingChargingCharacteristics  -- {PARAMETERS-BOUND : bound} --  ::= OCTET STRING (SIZE
    ( -- bound.& -- minAChBillingChargingLength.. -- bound.& -- maxAChBillingChargingLength))
    -- (CONSTRAINED BY { -- -- shall be the result of the BER-encoded value of the type --
    -- CAMEL-AchBillingChargingCharacteristics {bound}}) --
-- The AChBillingChargingCharacteristics parameter specifies the charging related information
-- to be provided by the gsmSSF and the conditions on which this information has to be reported
-- back to the gsmSCF with the ApplyChargingReport operation. The value of the
-- AChBillingChargingCharacteristics of type OCTET STRING carries a value of the ASN.1 data type:
-- CAMEL-AChBillingChargingCharacteristics. The normal encoding rules are used to encode this
-- value.
-- The violation of the UserDefinedConstraint shall be handled as an ASN.1 syntax error.

AChChargingAddress --{PARAMETERS-BOUND : bound}-- ::= CHOICE {
	legID				[2] LegID,
	srfConnection		[50] CallSegmentID --{bound}--
	}

AdditionalCallingPartyNumber  -- {PARAMETERS-BOUND : bound} --      ::= Digits -- {bound} --
-- Indicates the Additional Calling Party Number. 

AlertingPattern ::= OCTET STRING (SIZE(3))
-- Indicates a specific pattern that is used to alert a subscriber
-- (e.g. distinctive ringing, tones, etc.).
-- The encoding of the last octet of this parameter is as defined in 3GPP TS 29.002 [11].
-- Only the trailing OCTET is used, the remaining OCTETS shall be sent as NULL (zero)
-- The receiving side shall ignore the leading two OCTETS.

AOCBeforeAnswer ::= SEQUENCE {
	aOCInitial							[0] CAI-GSM0224,
	aOCSubsequent						[1] AOCSubsequent							OPTIONAL
	}

AOCGPRS ::= SEQUENCE {
	aOCInitial							[0] CAI-GSM0224,
	aOCSubsequent						[1] AOCSubsequent							OPTIONAL
	}

AOCSubsequent ::= SEQUENCE {
	cAI-GSM0224							[0] CAI-GSM0224	,
	tariffSwitchInterval				[1] INTEGER (1..86400)						OPTIONAL
	}
-- tariffSwitchInterval is measured in 1 second units

AppendFreeFormatData ::= ENUMERATED {
	overwrite	(0),
	append		(1)
	}

ApplicationTimer ::=INTEGER (0..2047)
-- Used by the gsmSCF to set a timer in the gsmSSF. The timer is in seconds.

AssistingSSPIPRoutingAddress --{PARAMETERS-BOUND : bound}-- ::= Digits --{bound}--
-- Indicates the destination address of the gsmSRF for the assist procedure.

AudibleIndicator ::= CHOICE {
	tone								 BOOLEAN,
	burstList							[1] BurstList
	}

BackwardServiceInteractionInd ::= SEQUENCE {
	conferenceTreatmentIndicator		[1] OCTET STRING (SIZE(1))					OPTIONAL,
	-- acceptConferenceRequest	'xxxx xx01'B
	-- rejectConferenceRequest	'xxxx xx10'B
	-- if absent from Connect or ContinueWithArgument,
	-- then CAMEL service does not affect conference treatement
	callCompletionTreatmentIndicator	 [2] OCTET STRING (SIZE(1))					OPTIONAL,
	-- acceptCallCompletionServiceRequest	'xxxx xx01'B,
	-- rejectCallCompletionServiceRequest	'xxxx xx10'B
	-- if absent from Connect or ContinueWithArgument,
	-- then CAMEL service does not affect call completion treatment
	...
	}

BasicGapCriteria --{PARAMETERS-BOUND : bound}-- ::= CHOICE {
	calledAddressValue					[0] Digits --{bound}--,
	gapOnService						[2] GapOnService,
	calledAddressAndService				[29] SEQUENCE {
		calledAddressValue					[0] Digits --{bound}--,
		serviceKey							[1] ServiceKey,
		...
		},
	callingAddressAndService			[30] SEQUENCE {
		callingAddressValue					[0] Digits --{bound}--,
		serviceKey							[1] ServiceKey,
		...
		}
	}
-- Both calledAddressValue and callingAddressValue can be
-- incomplete numbers, in the sense that a limited amount of digits can be given.
-- For the handling of numbers starting with the same digit string refer to the detailed
-- procedure of the CallGap operation

BCSMEvent ::= SEQUENCE {
	eventTypeBCSM						[0] EventTypeBCSM,
	monitorMode							[1] MonitorMode,
	legID								[2] LegID									OPTIONAL,
	dpSpecificCriteria					[30] DpSpecificCriteria						OPTIONAL,
	automaticRearm						[50] NULL									OPTIONAL
	}
-- Indicates the BCSM Event information for monitoring.

BCSM-Failure ::= SEQUENCE {
	legID								[0]	LegID									OPTIONAL,
	cause								[2]	Cause --{bound}--							OPTIONAL,
	...
	}

BearerCapability  -- {PARAMETERS-BOUND : bound} --  ::= CHOICE {
    bearerCap               [0] OCTET STRING (SIZE(2.. -- bound.& -- maxBearerCapabilityLength))
    }
-- Indicates the type of bearer capability connection to the user. For bearerCap, the ISUP User
-- Service Information, ETS 300 356-1 [8]
-- encoding shall be used. 

Burst ::= SEQUENCE {
	numberOfBursts						[0]	INTEGER (1..3)	DEFAULT 1,
	burstInterval						[1]	INTEGER	(1..20)							OPTIONAL,
	numberOfTonesInBurst				[2] INTEGER (1..3)	DEFAULT 3,
	toneDuration						[3]	INTEGER	(1..20)	DEFAULT 2,
	toneInterval						[4]	INTEGER	(1..20)	DEFAULT 2
	}
-- burstInterval, toneDurartion and toneInterval are measured in 100 millisecond units

BurstList ::= SEQUENCE {
	warningPeriod						[0] INTEGER	(1..1200) DEFAULT 30,
	bursts								[1] Burst
	}
-- warningPeriod is measured in 1 second units.

CAI-GSM0224 ::= SEQUENCE {
	e1									[0] INTEGER (0..8191)						OPTIONAL,
	e2									[1] INTEGER (0..8191)						OPTIONAL,
	e3									[2] INTEGER (0..8191)						OPTIONAL,
	e4									[3] INTEGER (0..8191)						OPTIONAL,
	e5									[4] INTEGER (0..8191)						OPTIONAL,
	e6									[5] INTEGER (0..8191)						OPTIONAL,
	e7									[6] INTEGER (0..8191)						OPTIONAL
	}
-- Indicates Charge Advice Information to the Mobile Station. For information regarding
-- parameter usage, refer to 3GPP TS 22.024 [2].

CalledPartyBCDNumber  -- {PARAMETERS-BOUND : bound} --      ::= OCTET STRING (SIZE(
             -- bound.& -- minCalledPartyBCDNumberLength ..
             -- bound.& -- maxCalledPartyBCDNumberLength))
-- Indicates the Called Party Number, including service selection information.
-- Refer to 3G TS 24.008 [12]
-- for encoding. This data type carries only the"type of number","numbering plan 
-- identification" and"number digit" fields defined in 3G TS 24.008 [12]; 
-- it does not carry the"called party 
-- BCD number IEI" or"length of called party BCD number contents".

CalledPartyNumber  -- {PARAMETERS-BOUND : bound} --     ::= OCTET STRING (SIZE
        ( -- bound.& -- minCalledPartyNumberLength.. -- bound.& -- maxCalledPartyNumberLength))
-- Indicates the Called Party Number. Refer to ITU-T Q.763 [20] for encoding.

-- A CalledPartyNumber may contain national-specific values of the Nature Of Address
-- indicator. The filling-in of the national-specific Nature Of Address indicator
-- values shall be done in accordance with the national ISUP of the gsmSSF country, e.g.
-- ANSI T1.113-1995 [92].
-- In terms of ETS EN 300 356-1 [23], the Destination Address Field is not present if the
-- destination address length is set to zero. This is the case e.g. when the ANSI
-- ISUP Nature Of Address indicator indicates no number present, operator requested
-- (1110100) or no number present, cut-through call to carrier (1110101).
-- See also see 3GPP TS 23.078 [7].

CallingPartyNumber  -- {PARAMETERS-BOUND : bound} --    ::= OCTET STRING (SIZE (
             -- bound.& -- minCallingPartyNumberLength..
             -- bound.& -- maxCallingPartyNumberLength))
-- Indicates the Calling Party Number. Refer to ETS 300 356?1 [8] for encoding.


CallResult  -- {PARAMETERS-BOUND : bound} --  ::= OCTET STRING (SIZE ( -- bound.& -- minCallResultLength ..
     -- bound.& -- maxCallResultLength))
    -- (CONSTRAINED BY { -- -- shall be the result of the BER-encoded value of type --
    -- CAMEL-CallResult {bound} }) --

-- The violation of the UserDefinedConstraint shall be handled as an ASN.1 syntax error.

-- This parameter provides the gsmSCF with the charging related information previously requested
-- using the ApplyCharging operation. This shall include the partyToCharge parameter as
-- received in the related ApplyCharging operation to correlate the result to the request


CallSegmentFailure --{PARAMETERS-BOUND : bound}-- ::= SEQUENCE {
	callSegmentID						[0] CallSegmentID --{bound}--					OPTIONAL,
	cause								[2]	Cause --{bound}--							OPTIONAL,
	...
	}

CallSegmentToCancel ::= SEQUENCE {
	invokeID							[0]	InvokeID								OPTIONAL,
	callSegmentID						[1]	CallSegmentID --{bound}--					OPTIONAL,
	...
	}


CAMEL-AChBillingChargingCharacteristics  -- {PARAMETERS-BOUND : bound} --  ::= CHOICE {
    timeDurationCharging                    [0] SEQUENCE {
            maxCallPeriodDuration               [0] INTEGER (1..864000),
            releaseIfdurationExceeded           [1]BOOLEAN DEFAULT FALSE,
            tariffSwitchInterval                [2] INTEGER (1..86400)          OPTIONAL,
            audibleIndicator                                [3] BOOLEAN DEFAULT FALSE,
            extensions                          [4] SEQUENCE SIZE(1.. -- bound.& -- numOfExtensions) OF 
                                                        ExtensionField   -- {bound} --  OPTIONAL,
            ...
        }
    }


-- tariffSwitchInterval is measured in 1 second units.
-- maxCallPeriodDuration is measured in100 millisecond units

CAMEL-CallResult --{PARAMETERS-BOUND : bound}-- ::= CHOICE {
	timeDurationChargingResult			[0] SEQUENCE {
		partyToCharge						[0] ReceivingSideID,
		timeInformation						[1] TimeInformation,
		callActive							[2] BOOLEAN DEFAULT TRUE,
		callReleasedAtTcpExpiry				[3] NULL								OPTIONAL,
		extensions							[4] SEQUENCE SIZE(1.. -- bound.& -- numOfExtensions) OF 
                                                        ExtensionField   -- {bound} --  OPTIONAL,
		aChChargingAddress					[5] AChChargingAddress --{bound}--
													,
		...
		}
	}

CAMEL-FCIBillingChargingCharacteristics --{PARAMETERS-BOUND : bound}-- ::= CHOICE{
	fCIBCCCAMELsequence1				[0] SEQUENCE {
			freeFormatData						[0] OCTET STRING (SIZE(
				--bound.&--minFCIBillingChargingDataLength .. --bound.&--maxFCIBillingChargingDataLength)),
		partyToCharge						[1] SendingSideID,
		appendFreeFormatData				[2] AppendFreeFormatData DEFAULT overwrite
		}
	}

CAMEL-FCIGPRSBillingChargingCharacteristics  -- {PARAMETERS-BOUND : bound} --  ::= SEQUENCE{
    gPRS-ReferenceNumber                    [0] GPRS-ReferenceNumber,
    fCIBCCCAMELsequence1                    [1] SEQUENCE {
        freeFormatData                          [0] OCTET STRING (SIZE
                                                        ( -- bound.& -- minFCIBillingChargingDataLength..
                                                         -- bound.& -- maxFCIBillingChargingDataLength)),
        pDPID                                   [1] PDPID OPTIONAL,
        appendFreeFormatData                    [2] AppendFreeFormatData    DEFAULT overwrite
        }
    }


CAMEL-FCISMSBillingChargingCharacteristics  -- {PARAMETERS-BOUND : bound} --  ::= CHOICE{
    fCIBCCCAMELsequence1        [0] SEQUENCE {
        freeFormatData              [0] OCTET STRING (SIZE ( -- bound.& -- minFCIBillingChargingDataLength..
                                                             -- bound.& -- maxFCIBillingChargingDataLength)),
        appendFreeFormatData        [1] AppendFreeFormatData DEFAULT overwrite
        }
    }

CAMEL-SCIBillingChargingCharacteristics ::= CHOICE {
	aOCBeforeAnswer						[0] AOCBeforeAnswer,
	aOCAfterAnswer						[1] AOCSubsequent
	}

CAMEL-SCIGPRSBillingChargingCharacteristics ::= SEQUENCE {
	aOCGPRS								[0] AOCGPRS,
	pDPID								[1] PDPID									OPTIONAL,
	...
	}

Carrier --{PARAMETERS-BOUND : bound}-- ::= OCTET STRING (SIZE(
	--bound.&--minCarrierLength .. --bound.&--maxCarrierLength))
-- This parameter is used for North America (na) only.
-- It contains the carrier selection field (first octet) followed by Carrier ID
-- information (North America (na)).

-- The Carrier selection is one octet and is encoded as:
-- 00000000		No indication
-- 00000001		Selected carrier identification code (CIC) pre subscribed and not
--				input by calling party
-- 00000010		Selected carrier identification code (CIC) pre subscribed and input by
--				calling party
-- 00000011		Selected carrier identification code (CIC) pre subscribed, no
--				indication of whether input by calling party (undetermined)
-- 00000100		Selected carrier identification code (CIC) not pre subscribed and
--				input by calling party
-- 00000101
--	to			Spare
-- 11111110
-- 11111111		Reserved

-- Refer to ANSI T1.113-1995 [92] for encoding of na carrier ID information (3 octets).

Cause --{PARAMETERS-BOUND : bound}-- ::= OCTET STRING (SIZE(
	--bound.&--minCauseLength .. --bound.&--maxCauseLength))
-- Indicates the cause for interface related information.
-- Refer to ETSI EN 300 356-1 [23] Cause parameter for encoding.
-- For the use of cause and location values refer to ITU-T Recommendation Q.850 [47]
-- Shall always include the cause value and shall also include the diagnostics field,
-- if available.

CGEncountered ::= ENUMERATED {
	noCGencountered						(0),
	manualCGencountered					(1),
	scpOverload							(2)
	}
-- Indicates the type of automatic call gapping encountered, if any.

ChargeNumber --{PARAMETERS-BOUND : bound}-- ::= LocationNumber --{bound}--
-- Information sent in either direction indicating the chargeable number for the call and
-- consisting of the odd/even indicator, nature of address indicator, numbering plan indicator,
-- and address signals.

-- Uses the LocationNumber format which is based on the Location Number format as defined
-- in ITU-T Recommendation Q.763 [45].
-- For example, the ChargeNumber may be a third party number to which a call is billed for
-- the 3rd party billing service. In this case, the calling party may request operator assistance
-- to charge the call to, for example, their home number.

-- For NA, this parameter uniquely identifies the chargeable number for a call sent into a North
-- American long distance carrier. It transports the ChargeNumber Parameter Field as defined in
-- ANSI T1.113-1995 [92]. This provides
--  - 1 octet for the nature of address indicator field, plus
--  - 1 octet for a numbering plan field, plus
--  - up to 5 octets for the address signal (up to 10 digits)

-- The Charge Number in ANSI T1.113-1995 [92] normally contains a 10 digit national number within
-- the North American Numbering Plan (NANP); longer (e.g. international) charge numbers are not
-- supported in ANSI T1.113-1995 [92].

ChargeUnitsComponent ::= SEQUENCE SIZE
			(--bound.&--minComponentLength .. --bound.&--maxComponentLength) OF SEQUENCE {
	monitorComponent					[0] MonitorComponent,
	reportingConditionUnits				[1] ReportingConditionUnits
	}

ChargeUnitsTotal ::= SEQUENCE {
	reportingConditionUnits [0] ReportingConditionUnits
	}

ChargingCharacteristics ::= CHOICE {
	maxTransferredVolume				[0]	INTEGER (1..4294967295),
	maxElapsedTime						[1] INTEGER (1..86400)
	}
--	maxTransferredVolume is measured in number of bytes
--	maxElapsedTime is measured in seconds

ChargingResult ::= CHOICE {
	transferredVolume					[0] TransferredVolume,
	elapsedTime							[1]	ElapsedTime
	}

ChargingRollOver ::= CHOICE {
	transferredVolumeRollOver			[0] TransferredVolumeRollOver,
	elapsedTimeRollOver					[1]	ElapsedTimeRollOver
	}
-- transferredVolumeRollOver shall be reported if ApplyChargingReportGPRS reports volume and
-- a roll-over has occurred in one or more volume counters. Otherwise, it shall be absent.
-- elapsedTimeRollOver shall be reported if ApplyChargingReportGPRS reports duration and
-- a roll-over has occurred in one or more duration counters. Otherwise, it shall be absent.

CollectedDigits ::= SEQUENCE {
	minimumNbOfDigits					[0] INTEGER (1..30)	DEFAULT 1,
	maximumNbOfDigits					[1] INTEGER (1..30),
	endOfReplyDigit						[2] OCTET STRING (SIZE (1..2))				OPTIONAL,
	cancelDigit							[3] OCTET STRING (SIZE (1..2))				OPTIONAL,
	startDigit							[4] OCTET STRING (SIZE (1..2))				OPTIONAL,
	firstDigitTimeOut					[5] INTEGER (1..127)						OPTIONAL,
	interDigitTimeOut					[6] INTEGER (1..127)						OPTIONAL,
	errorTreatment						[7] ErrorTreatment DEFAULT stdErrorAndInfo,
	interruptableAnnInd					[8] BOOLEAN DEFAULT TRUE,
	voiceInformation					[9] BOOLEAN DEFAULT FALSE,
	voiceBack							[10] BOOLEAN DEFAULT FALSE
	}
-- The use of voiceBack and the support of voice recognition via voiceInformation
-- is network operator specific.
-- The endOfReplyDigit, cancelDigit, and startDigit parameters have been
-- designated as OCTET STRING, and are to be encoded as BCD, one digit per octet
-- only, contained in the four least significant bits of each OCTET. The following encoding shall
-- be applied for the non-decimal characters:
-- 1011 (*), 1100 (#).
-- The usage is service dependent.
-- firstDigitTimeOut and interDigitTimeOut are measured in seconds.

CollectedInfo ::= CHOICE {
	collectedDigits						[0] CollectedDigits
	}

ConnectedNumberTreatmentInd ::= ENUMERATED {
	noINImpact							(0),
	presentationRestricted				(1),
	presentCalledINNumber				(2),
	presentCallINNumberRestricted		(3)
}
-- This parameter is used to suppress or to display the connected number.

ControlType ::= ENUMERATED {
	sCPOverloaded						(0),
	manuallyInitiated					(1)
	}

CompoundCriteria --{PARAMETERS-BOUND : bound}-- ::= SEQUENCE {
	basicGapCriteria					[0] BasicGapCriteria --{bound}--,
	scfID								[1] ScfID --{bound}--							OPTIONAL
	}

CorrelationID --{PARAMETERS-BOUND : bound}-- ::= Digits --{bound}--
-- used by gsmSCF for correlation with a previous operation.

DateAndTime ::= OCTET STRING (SIZE(7))
--  DateAndTime is BCD encoded. The year digit indicating millenium occupies bits
--  0-3 of the first octet, and the year digit indicating century occupies bits
--  4-7 of the first octet.
--  The year digit indicating decade occupies bits 0-3 of the second octet,
--  whilst the digit indicating the year within the decade occupies bits 4-7 of
--  the second octet.
--  The most significant month digit occupies bits 0-3 of the third octet,
--  and the least significant month digit occupies bits 4-7 of the third octet.
--  The most significant day digit occupies bits 0-3 of the fourth octet,
--  and the least significant day digit occupies bits 4-7 of the fourth octet.
--  The most significant hours digit occupies bits 0-3 of the fifth octet,
--  and the least significant digit occupies bits 4-7 of the fifth octet.
--  The most significant minutes digit occupies bits 0-3 of the sixth octet,
--  and the least significant digit occupies bits 4-7 of the sixth octet.
--  The most significant seconds digit occupies bits 0-3 of the seventh octet,
--  and the least seconds significant digit occupies bits 4-7 of the seventh octet.
--  For the encoding of digits in an octet, refer to the timeAndtimezone parameter.

DestinationRoutingAddress  -- {PARAMETERS-BOUND : bound} --  ::= SEQUENCE SIZE(1) OF
CalledPartyNumber  -- {bound} -- 
-- Indicates the Called Party Number.

Digits --{PARAMETERS-BOUND : bound}-- ::= OCTET STRING (SIZE(
	--bound.&--minDigitsLength .. --bound.&--maxDigitsLength))
-- Indicates the address signalling digits.
-- Refer to ETSI EN 300 356-1 [23] Generic Number & Generic Digits parameters for encoding.
-- The coding of the subfields "NumberQualifier" in Generic Number and "TypeOfDigits" in
-- Generic Digits are irrelevant to the CAP;
-- the ASN.1 tags are sufficient to identify the parameter.
-- The ISUP format does not allow to exclude these subfields,
-- therefore the value is network operator specific.
--
-- The following parameters shall use Generic Number:
--  - AdditionalCallingPartyNumber for InitialDP
--  - AssistingSSPIPRoutingAddress for EstablishTemporaryConnection
--  - CorrelationID for AssistRequestInstructions
--  - CalledAddressValue for all occurrences, CallingAddressValue for all occurrences.
--
-- The following parameters shall use Generic Digits:
--  - CorrelationID in EstablishTemporaryConnection
--  - number in VariablePart
--  - digitsResponse in ReceivedInformationArg
--	- midCallEvents in oMidCallSpecificInfo and tMidCallSpecificInfo
--
-- In the digitsResponse and midCallevents, the digits may also include the '*', '#',
-- a, b, c and d digits by using the IA5 character encoding scheme. If the BCD even or
-- BCD odd encoding scheme is used, then the following encoding shall be applied for the
-- non-decimal characters: 1011 (*), 1100 (#).

-- Note that when CorrelationID is transported in Generic Digits, then the digits shall
-- always be BCD encoded.

DpSpecificCriteria ::= CHOICE {
	applicationTimer					[1] ApplicationTimer,
	midCallControlInfo					[2]	MidCallControlInfo
	}
--  The gsmSCF may set a timer in the gsmSSF for the No_Answer event.
--  If the user does not answer the call within the allotted time,
--  then the gsmSSF reports the event to the gsmSCF.
--	The gsmSCF may define a criterion for the detection of DTMF digits during a call.

ElapsedTime ::= CHOICE {
	timeGPRSIfNoTariffSwitch			[0] INTEGER (0..86400),
	timeGPRSIfTariffSwitch				[1] SEQUENCE {
		timeGPRSSinceLastTariffSwitch		[0] INTEGER (0..86400),
		timeGPRSTariffSwitchInterval		[1] INTEGER (0..86400)					OPTIONAL
		}
	}
--	timeGPRSIfNoTariffSwitch is measured in seconds
--	timeGPRSSinceLastTariffSwitch and timeGPRSTariffSwitchInterval are measured in seconds

ElapsedTimeRollOver ::= CHOICE {
	rO-TimeGPRSIfNoTariffSwitch			[0] INTEGER (0..255),
	rO-TimeGPRSIfTariffSwitch			[1] SEQUENCE {
		rO-TimeGPRSSinceLastTariffSwitch 	[0] INTEGER (0..255)					OPTIONAL,
		rO-TimeGPRSTariffSwitchInterval		[1] INTEGER (0..255)					OPTIONAL
		}
	}
--	rO-TimeGPRSIfNoTariffSwitch, rO-TimeGPRSSinceLastTariffSwitch and
--	rO-TimeGPRSTariffSwitchInterval
--	present counters indicating the number of parameter range rollovers.

EndUserAddress --{PARAMETERS-BOUND: bound}-- ::= SEQUENCE {
	pDPTypeOrganization					[0] OCTET STRING (SIZE(1)),
	pDPTypeNumber						[1] OCTET STRING (SIZE(1)),
	pDPAddress							[2] OCTET STRING (SIZE(
		--bound.&--minPDPAddressLength .. --bound.&--maxPDPAddressLength))					OPTIONAL
	}
-- Indicates the EndUserAddress, refer to 3GPP TS 29.060 [12] for the encoding.
-- The pDPTypeOrganization shall use the least significant 4 bits of the octet encoded.
-- The sender of this parameter shall set the most significant 4 bits of the octet to 1.
-- The receiver of this parameter shall ignore the most significant 4 bits of this octet.

ErrorTreatment ::= ENUMERATED {
	stdErrorAndInfo						(0),
	help								(1),
	repeatPrompt						(2)
	}
-- stdErrorAndInfomeans returning the "ImproperCallerResponse" error in the event of an error
-- condition during collection of user info.

EvaluesAndTsw ::= SEQUENCE {
	evalues								[0] CAI-GSM0224,
	tariffSwitchInterval				[1] TariffSwitchInterval
	}

EvaluesComponent ::= SEQUENCE SIZE
		(--bound.&--minComponentLength .. --bound.&--maxComponentLength) OF SEQUENCE {
	monitorComponent					[0] MonitorComponent,
	reportingConditionEvalue			[1] ReportingConditionEvalue
	}

EvaluesTotal ::= SEQUENCE {
	reportingConditionEvalue			[0] ReportingConditionEvalue
	}

EventSpecificChargingInformation --{PARAMETERS-BOUND : bound}-- ::= CHOICE {
	infoChargeUnitsTotal				[0] InfoChargeUnitsTotal,
	infoChargeUnitsComponents			[1] InfoChargeUnitsComponents --{bound}--,
	infoEvalueTotal						[2] InfoEvalueTotal,
	infoEvalueComponents				[3] InfoEvalueComponents --{bound}--
	}

EventSpecificInformationBCSM --{PARAMETERS-BOUND : bound}-- ::= CHOICE {
	routeSelectFailureSpecificInfo		[2] SEQUENCE {
		failureCause						[0] Cause --{bound}--						OPTIONAL,
		...
		},
	oCalledPartyBusySpecificInfo		[3] SEQUENCE {
		busyCause							[0] Cause --{bound}--					OPTIONAL,
		...
		},
	oNoAnswerSpecificInfo				[4] SEQUENCE {
		-- no specific info defined --
		...
		},
	oAnswerSpecificInfo					[5] SEQUENCE {
		destinationAddress					[50] CalledPartyNumber --{bound}--			OPTIONAL,
		or-Call								[51] NULL								OPTIONAL,
		forwardedCall						[52] NULL								OPTIONAL,
		...
		},
	oMidCallSpecificInfo				[6] SEQUENCE {
		midCallEvents						[1] CHOICE {
			dTMFDigitsCompleted					[3] Digits,
			dTMFDigitsTimeOut					[4] Digits
			}																		OPTIONAL,
		...
		},
	oDisconnectSpecificInfo				[7] SEQUENCE {
		releaseCause						[0] Cause --{bound}--						OPTIONAL,
		...
		},
	tBusySpecificInfo					[8] SEQUENCE {
		busyCause							[0] Cause {bound}						OPTIONAL,
		callForwarded						[50] NULL								OPTIONAL,
		routeNotPermitted					[51] NULL								OPTIONAL,
		forwardingDestinationNumber			[52] CalledPartyNumber --{bound}--			OPTIONAL,
		...
		},
	tNoAnswerSpecificInfo				[9] SEQUENCE {
		callForwarded						[50] NULL								OPTIONAL,
		forwardingDestinationNumber			[52] CalledPartyNumber --{bound}--			OPTIONAL,
		...
		},
	tAnswerSpecificInfo					[10] SEQUENCE {
		destinationAddress					[50] CalledPartyNumber --{bound}--			OPTIONAL,
		or-Call								[51] NULL								OPTIONAL,
		forwardedCall						[52] NULL								OPTIONAL,
		...
		},
	tMidCallSpecificInfo				[11] SEQUENCE {
		midCallEvents						[1] CHOICE {
			dTMFDigitsCompleted					[3] Digits,
			dTMFDigitsTimeOut					[4] Digits
			}																		OPTIONAL,
		...
		},
	tDisconnectSpecificInfo				[12] SEQUENCE {
		releaseCause						[0] Cause --{bound}--						OPTIONAL,
		...
		},
	oTermSeizedSpecificInfo				[13] SEQUENCE {
		locationInformation					[50] LocationInformation				OPTIONAL,
		...
		},
	callAcceptedSpecificInfo			[20] SEQUENCE {
		locationInformation					[50] LocationInformation				OPTIONAL,
		...
		},
	oAbandonSpecificInfo				[21] SEQUENCE {
		routeNotPermitted					[50] NULL								OPTIONAL,
		...
		},
	oChangeOfPositionSpecificInfo		[50] SEQUENCE {
		locationInformation					[50] LocationInformation				OPTIONAL,
		...
		},
	tChangeOfPositionSpecificInfo		[51] SEQUENCE {
		locationInformation					[50] LocationInformation				OPTIONAL,
		...
		}
	}
-- Indicates the call related information specific to the event.

EventSpecificInformationSMS ::= CHOICE {
	o-smsFailureSpecificInfo			[0] SEQUENCE {
		failureCause						[0] MO-SMSCause							OPTIONAL,
		...
		},
	o-smsSubmissionSpecificInfo			[1] SEQUENCE {
		-- no specific info defined-
		...
		},
	t-smsFailureSpecificInfo			[2] SEQUENCE {
		failureCause						[0] MT-SMSCause							OPTIONAL,
		...
		},
	t-smsDeliverySpecificInfo			[3] SEQUENCE {
		-- no specific info defined-
		...
		}
	}

EventTypeBCSM ::= ENUMERATED {
	collectedInfo						(2),
	analyzedInformation					(3),
	routeSelectFailure					(4),
	oCalledPartyBusy					(5),
	oNoAnswer							(6),
	oAnswer								(7),
	oMidCall							(8),
	oDisconnect							(9),
	oAbandon							(10),
	termAttemptAuthorized				(12),
	tBusy								(13),
	tNoAnswer							(14),
	tAnswer								(15),
	tMidCall							(16),
	tDisconnect							(17),
	tAbandon							(18),
	oTermSeized							(19),
	callAccepted						(27),
	oChangeOfPosition					(50),
	tChangeOfPosition					(51)
	}
-- Indicates the BCSM detection point event.
-- Values collectedInfo, analyzedInformation and termAttemptAuthorized may be used
-- for TDPs only.

EventTypeChargingPLMN --{PARAMETERS-BOUND : bound}-- ::= CHOICE {
	chargeUnitsTotal					[0] ChargeUnitsTotal,
	chargeUnitsComponent				[1] ChargeUnitsComponent --{bound}--,
	evaluesTotal						[2] EvaluesTotal,
	evaluesComponent					[3] EvaluesComponent --{bound}--
	}
-- This parameter indicates the charging event type.

EventTypeSMS ::= ENUMERATED {
	sms-CollectedInfo					(1),
	o-smsFailure						(2),
	o-smsSubmission						(3),
	sms-DeliveryRequested				(11),
	t-smsFailure						(12),
	t-smsDelivery						(13)
	}
-- Values sms-CollectedInfo and sms-DeliveryRequested may be used for TDPs only.

--change for compiler ExtensionField {PARAMETERS-BOUND : bound}             ::= SEQUENCE {
--change for compiler   type    EXTENSION.&id ({SupportedExtensions {bound}}),   
-- shall identify the value of an EXTENSION type
--change for compiler   criticality CriticalityType                                 DEFAULT ignore,
--change for compiler   value                   [1] EXTENSION.&ExtensionType    
--change for compiler              ({SupportedExtensions {bound}}{@type}),
--change for compiler   ...
--change for compiler   }

-- This parameter indicates an extension of an argument data type. 
-- Its content is network operator specific


------------------------------------------------------------
-- Replacement for type ExtensionField.
------------------------------------------------------------

ExtensionField ::= SEQUENCE {
    type            INTEGER,
    criticality     CriticalityType,
    value           [1] ANY
    }



FCIBillingChargingCharacteristics  -- {PARAMETERS-BOUND : bound} --  ::= OCTET STRING (SIZE
    ( -- bound.& -- minFCIBillingChargingLength.. -- bound.& -- maxFCIBillingChargingLength))
    -- (CONSTRAINED BY { -- -- shall be the result of the BER-encoded value of type - --
    -- CAMEL-FCIBillingChargingCharacteristics {bound}}) --
-- This parameter indicates the billing and/or charging characteristics. 
-- The violation of the UserDefinedConstraint shall be handled as an ASN.1 syntax error.

FCIGPRSBillingChargingCharacteristics  -- {PARAMETERS-BOUND : bound} --  ::= OCTET STRING (SIZE
    ( -- bound.& -- minFCIBillingChargingLength.. -- bound.& -- maxFCIBillingChargingLength))
    -- (CONSTRAINED BY {-- -- shall be the result of the BER-encoded value of type - --
    -- CAMEL-FCIGPRSBillingChargingCharacteristics {bound}}) --
-- This parameter indicates the GPRS billing and/or charging characteristics. 
-- The violation of the UserDefinedConstraint shall be handled as an ASN.1 syntax error.

FCISMSBillingChargingCharacteristics  -- {PARAMETERS-BOUND : bound} --  ::= OCTET STRING (SIZE
    ( -- bound.& -- minFCIBillingChargingLength.. -- bound.& -- maxFCIBillingChargingLength))
    -- (CONSTRAINED BY {-- -- shall be the result of the BER-encoded value of type - --
    -- CAMEL-FCISMSBillingChargingCharacteristics {bound}}) --
-- This parameter indicates the SMS billing and/or charging characteristics. 
-- The violation of the UserDefinedConstraint shall be handled as an ASN.1 syntax error.

ForwardServiceInteractionInd ::= SEQUENCE {
	conferenceTreatmentIndicator		[1] OCTET STRING (SIZE(1))					OPTIONAL,
	-- acceptConferenceRequest	'xxxx xx01'B
	-- rejectConferenceRequest	'xxxx xx10'B
	-- if absent from Connect or ContinueWithArgument,
	-- then CAMEL service does not affect conference treatment
	callDiversionTreatmentIndicator		[2] OCTET STRING (SIZE(1))					OPTIONAL,
	-- callDiversionAllowed		'xxxx xx01'B
	-- callDiversionNotAllowed	'xxxx xx10'B
	-- if absent from Connect or ContinueWithArgument,
	-- then CAMEL service does not affect call diversion treatment
	callingPartyRestrictionIndicator	[4] OCTET STRING (SIZE(1))					OPTIONAL,
	-- noINImpact				'xxxx xx01'B
	-- presentationRestricted	'xxxx xx10'B
	-- if absent from Connect or ContinueWithArgument,
	-- then CAMEL service does not affect calling party restriction treatment
...
	}

GapCriteria --{PARAMETERS-BOUND : bound}--::= CHOICE {
	basicGapCriteria					BasicGapCriteria --{bound}--,
	compoundGapCriteria					CompoundCriteria --{bound}--
	}

GapIndicators ::= SEQUENCE {
	duration							[0] Duration,
	gapInterval							[1] Interval,
	...
	}
-- Indicates the call gapping characteristics.
-- No call gapping when gapInterval equals 0.

GapOnService ::= SEQUENCE {
	serviceKey							[0] ServiceKey,
	...
	}

GapTreatment --{PARAMETERS-BOUND : bound}-- ::= CHOICE {
	informationToSend					[0] InformationToSend --{bound}--,
	releaseCause						[1] Cause --{bound}--
	}
-- The default value for Cause is the same as in ISUP.

GenericNumber --{PARAMETERS-BOUND : bound}-- ::= OCTET STRING (SIZE(
	--bound.&--minGenericNumberLength .. --bound.&--maxGenericNumberLength))
-- Indicates a generic number. Refer to ETSI EN 300 356-1 [23] Generic number for encoding.

GenericNumbers --{PARAMETERS-BOUND : bound}-- ::= SET SIZE(1..--bound.&--numOfGenericNumbers) OF GenericNumber --{bound}--

GPRS-QoS ::= CHOICE {
	short-QoS-format					[0]	QoS-Subscribed,
	long-QoS-format						[1]	Ext-QoS-Subscribed
	}
-- Short-QoS-format shall be sent for QoS in pre GSM release 99 format.
-- Long-QoS-format shall be sent for QoS in GSM release 99 (and beyond) format.
-- Which of the two QoS formats shall be sent is determined by which QoS
-- format is available in the SGSN at the time of sending.
-- Refer to 3GPP TS 29.002 [11] for encoding details of QoS-Subscribed and
-- Ext-QoS-Subscribed.

GPRSCause --{PARAMETERS-BOUND : bound}-- ::= OCTET STRING (SIZE
			(--bound.&--minGPRSCauseLength .. --bound.&--maxGPRSCauseLength))
-- Shall only include the cause value.

--	00000000   Unspecified
--  All other values shall be interpreted as "Unspecified".
--
-- This parameter indicates the cause for CAP interface related information.
-- The GPRSCause mapping to/from GTP cause values specified in the 3GPP TS 29.060 [12] and
-- to/from 3GPP TS 24.008 [9] GMM cause and SM cause values are outside scope of this document.

GPRSEvent ::= SEQUENCE {
	gPRSEventType						[0] GPRSEventType,
	monitorMode							[1] MonitorMode
	}
--  Indicates the GPRS event information for monitoring.

LocationInformationGPRS     ::= SEQUENCE {
        cellGlobalIdOrServiceAreaIdOrLAI    [0] OCTET STRING (SIZE(5..7))   OPTIONAL,
        geographicalInformation         [1] OCTET STRING (SIZE (8))         OPTIONAL,
        sgsn-Number                         [2] ISDN-AddressString          OPTIONAL
}

GPRSChargingID                          ::= INTEGER (0..4294967295)

GPRSEventSpecificInformation --{PARAMETERS-BOUND : bound}-- ::= CHOICE {

	attachChangeOfPositionSpecificInformation
										[0] SEQUENCE {
			locationInformationGPRS			[0] LocationInformationGPRS				OPTIONAL,
			...
			},

	pdp-ContextchangeOfPositionSpecificInformation
										[1] SEQUENCE {
			accessPointName					[0]	AccessPointName --{bound}--				OPTIONAL,
			chargingID						[1]	GPRSChargingID						OPTIONAL,
			locationInformationGPRS			[2] LocationInformationGPRS 			OPTIONAL,
			endUserAddress					[3]	EndUserAddress --{bound}--				OPTIONAL,
			qualityOfService				[4]	QualityOfService					OPTIONAL,
			timeAndTimeZone					[5]	TimeAndTimezone --{bound}-- 			OPTIONAL,
			...,
			gGSNAddress						[6]	GSN-Address							OPTIONAL
			},

	detachSpecificInformation			[2] SEQUENCE {
			initiatingEntity				[0] InitiatingEntity					OPTIONAL,
			...,
			routeingAreaUpdate				[1]	NULL								OPTIONAL
			},

	disconnectSpecificInformation		[3] SEQUENCE {
			initiatingEntity				[0] InitiatingEntity					OPTIONAL,
			...,
			routeingAreaUpdate				[1]	NULL								OPTIONAL
			},

	pDPContextEstablishmentSpecificInformation
										[4]	SEQUENCE {
			accessPointName					[0]	AccessPointName --{bound}--				OPTIONAL,
			endUserAddress					[1]	EndUserAddress --{bound}--				OPTIONAL,
			qualityOfService				[2]	QualityOfService					OPTIONAL,
			locationInformationGPRS			[3] LocationInformationGPRS 			OPTIONAL,
			timeAndTimeZone					[4]	TimeAndTimezone --{bound}-- 			OPTIONAL,
			pDPInitiationType				[5] PDPInitiationType					OPTIONAL,
			...,
			secondaryPDP-context			[6] NULL								OPTIONAL
			},

	pDPContextEstablishmentAcknowledgementSpecificInformation
										[5]	SEQUENCE {
			accessPointName					[0]	AccessPointName --{bound}--			OPTIONAL,
			chargingID						[1] GPRSChargingID						OPTIONAL,
			endUserAddress					[2]	EndUserAddress --{bounbd}--				OPTIONAL,
			qualityOfService				[3]	QualityOfService					OPTIONAL,
			locationInformationGPRS			[4] LocationInformationGPRS 			OPTIONAL,
			timeAndTimeZone					[5]	TimeAndTimezone --{bound}-- 			OPTIONAL,
			...,
			gGSNAddress						[6]	GSN-Address							OPTIONAL
			}
		}

GPRSEventType ::= ENUMERATED {
	attach								(1),
	attachChangeOfPosition				(2),
	detached							(3),
	pdp-ContextEstablishment			(11),
	pdp-ContextEstablishmentAcknowledgement (12),
	disonnect							(13),
	pdp-ContextChangeOfPosition			(14)
	}

InbandInfo --{PARAMETERS-BOUND : bound}-- ::= SEQUENCE {
	messageID							[0] MessageID --{bound}--,
	numberOfRepetitions					[1] INTEGER (1..127)						OPTIONAL,
	duration							[2] INTEGER (0..32767)						OPTIONAL,
	interval							[3] INTEGER (0..32767)						OPTIONAL,
...
	}
-- Interval is the time in seconds between each repeated announcement. Duration is the total
-- amount of time in seconds, including repetitions and intervals.
-- The end of announcement is either the end of duration or numberOfRepetitions,
-- whatever comes first.
-- duration with value 0 indicates infinite duration

InfoChargeUnitsComponents ::= SEQUENCE SIZE
		(--bound.&--minComponentLength .. --bound.&--maxComponentLength) OF SEQUENCE {
	reportingConditionUnits				[0] ReportingConditionUnits,
	units								[1] Units,
	monitorComponent					[2] MonitorComponent
	}

InfoChargeUnitsTotal ::= SEQUENCE {
	reportingConditionUnits				[0] ReportingConditionUnits,
	units								[1] Units
	}

InfoEvalueComponents ::= SEQUENCE SIZE
		(--bound.&--minComponentLength .. --bound.&--maxComponentLength) OF SEQUENCE {
	reportingConditionEvalue			[0] ReportingConditionEvalue,
	evaluesAndTsw						[1] EvaluesAndTsw,
	monitorComponent					[2] MonitorComponent
	}

InfoEvalueTotal ::= SEQUENCE {
	reportingConditionEvalue			[0]	ReportingConditionEvalue,
	evaluesAndTsw						[1] EvaluesAndTsw
	}

InformationToSend --{PARAMETERS-BOUND : bound}-- ::= CHOICE {
	inbandInfo							[0] InbandInfo --{bound}--,
	tone								[1] Tone
	}

InitiatingEntity ::= ENUMERATED {
	mobileStation						(0),
	sgsn								(1),
	hlr									(2),
	ggsn								(3)
	}

InvokeID ::= TCInvokeIdSet

IPRoutingAddress --{PARAMETERS-BOUND : bound}-- ::= CalledPartyNumber --{bound}--
-- Indicates the routeing address for the IP.

IPSSPCapabilities --{PARAMETERS-BOUND : bound}-- ::= OCTET STRING (SIZE(
	--bound.&--minIPSSPCapabilitiesLength .. --bound.&--maxIPSSPCapabilitiesLength))
--  Indicates the gsmSRF resources available. The parameter has two parts, a standard and a
--  bilateral part. The standard part indicates capabilities defined as optional in CAP V.2
--  that shall be recognised (but not necessarily supported) by a CAP V.2 gsmSCF. The bilateral
--  part contains further information that is not specified in this standard, but which is set
--  according to bilateral agreements between network operators and/or equipment vendors.
--  The last octet of the standard part is indicated by bit 7 being set to 0, otherwise Bit 7 of
--  a standard part octet is set to 1 indicating that the standard part continues in the following
--  octet. Coding is as follows:

--  Octet 1					Standard Part for CAP V.3
--  Bit	Value				Meaning
--  0	0					IPRoutingAddress not supported
--		1					IPRoutingAddress supported
--  1	0					VoiceBack not supported
--		1					VoiceBack supported
--  2	0					VoiceInformation not supported, via speech recognition
--		1					VoiceInformation supported, via speech recognition
--  3	0					VoiceInformation not supported, via voice recognition
--		1					VoiceInformation supported, via voice recognition
--  4	0					Generation of voice announcements from Text not supported
--		1					Generation of voice announcements from Text supported
--  5	-					Reserved
--  6	-					Reserved
--  7	0					End of standard part
-- 		1					This value is reserved in CAP V.3
--
--  Octets 2 to 4			Bilateral Part: Network operator/equipment vendor specific

LegOrCallSegment ::= CHOICE {
	callSegmentID						[0] CallSegmentID --{bound}--,
	legID								[1] LegID
	}

LegType ::= OCTET STRING (SIZE(1))
leg1 LegType	::= '01'H
leg2 LegType	::= '02'H

LocationNumber --{PARAMETERS-BOUND : bound}-- ::= OCTET STRING (SIZE (
	--bound.&--minLocationNumberLength .. --bound.&--maxLocationNumberLength))
-- Indicates the Location Number for the calling party.
-- Refer to ETSI EN 300 356-1 [23] for encoding.

MessageID --{PARAMETERS-BOUND : bound}-- ::= CHOICE {
	elementaryMessageID					[0] Integer4,
	text								[1] SEQUENCE {
		messageContent						[0] IA5String (SIZE(
			--bound.&--minMessageContentLength .. --bound.&--maxMessageContentLength)),
		attributes							[1] OCTET STRING (SIZE(
			--bound.&--minAttributesLength .. --bound.&--maxAttributesLength)) 				OPTIONAL
	},
	elementaryMessageIDs				[29] SEQUENCE SIZE (1.. --bound.&--numOfMessageIDs) OF Integer4,
	variableMessage						[30] SEQUENCE {
		elementaryMessageID					[0] Integer4,
		variableParts						[1] SEQUENCE SIZE (1..5) OF VariablePart --{bound}--
		}
	}
-- Use of the text parameter is network operator/equipment vendor specific.

MidCallControlInfo ::= SEQUENCE {
	minimumNumberOfDigits				[0]	INTEGER (1..30) DEFAULT 1,
	maximumNumberOfDigits				[1]	INTEGER (1..30) DEFAULT 30,
	endOfReplyDigit						[2]	OCTET STRING (SIZE (1..2))				OPTIONAL,
	cancelDigit							[3]	OCTET STRING (SIZE (1..2))				OPTIONAL,
	startDigit							[4]	OCTET STRING (SIZE (1..2))				OPTIONAL,
	interDigitTimeout					[6]	INTEGER (1..127) DEFAULT 10
	}
--
-- - minimumNumberOfDigits			specifies the minumum number of digits that shall be collected
-- - maximumNumberOfDigits			specifies the maximum number of digits that shall be collected
-- - endOfReplyDigit				specifies the digit string that denotes the end of the digits
--									to be collected.
-- - cancelDigit					specifies the digit string that indicates that the input shall
--									be erased and digit collection shall start afresh.
-- - startDigit						specifies the digit string that denotes the start of the digits
--									to be collected.
-- - interDigitTimeout				specifies the maximum duration in seconds between successive
--									digits.
--
-- endOfReplyDigit, cancelDigit and startDigit shall contain digits in the range 0..9, '*' and '#'
-- only. The collected digits string, reported to the gsmSCF, shall include the endOfReplyDigit and
-- the startDigit, if present.
--
-- endOfReplyDigit, cancelDigit and startDigit shall be encoded as BCD digits. Each octet shall
-- contain one BCD digit, in the 4 least significant bits of each octet.
-- The following encoding shall be used for the over-decadic digits: 1011 (*), 1100 (#).

MonitorComponent ::= ENUMERATED {
	chargesTransitNetwork				(0),
	chargesSpecificPLMN					(1)
	}

MonitorMode ::= ENUMERATED {
	interrupted							(0),
	notifyAndContinue					(1),
	transparent							(2)
	}
-- Indicates the event is relayed and/or processed by the SSP.
-- Transparent means that the gsmSSF or gprsSSF does not notify the gsmSCF of the event.
-- For the use of this parameter refer to the procedure descriptions in clause 11.
-- For the RequestNotificationCharging operation, "interrupted" shall not be used in MonitorMode.

MO-SMSCause ::= ENUMERATED {
	systemFailure						(0),
	unexpectedDataValue					(1),
	facilityNotSupported				(2),
	sM-DeliveryFailure					(3),
 	releaseFromRadioInterface			(4)
	}
-- MO SMS error values which are reported to gsmSCF.
-- Most of these values are received from the SMSC as a response to
-- MO-ForwardSM operation.

MT-SMSCause ::= OCTET STRING (SIZE (1))
-- This variable is sent to the gsmSCF for a Short Message delivery failure
-- notification.
-- If the delivery failure is due to RP-ERROR RPDU received from the MS,
-- then MT-SMSCause shall be set to the RP-Cause component in the RP-ERROR RPDU.
-- Refer to 3G TS 24.011 [10] for the encoding of RP-Cause values.
-- Otherwise, if the delivery failure is due to internal failure in the MSC or SGSN
-- or time-out from the MS, then MT-SMSCause shall be set to "Protocol error,
-- unspecified", as defined in 3G TS 24.011 [10].

NAOliInfo ::= OCTET STRING (SIZE (1))
--  NA Oli information takes the same value as defined in ANSI T1.113-1995 [92]
--  e.g.	'3D'H  - Decimal value 61 - Cellular Service (Type 1)
--			'3E'H  - Decimal value 62 - Cellular Service (Type 2)
--			'3F'H  - Decimal value 63 - Cellular Service (roaming)

OCSIApplicable ::= NULL
--  Indicates that the Originating CAMEL Subscription Information, if present, shall be 
--  applied on the outgoing call leg created with a Connect operation. For the use of this 
--  parameter see 3GPP TS 23.078 [7].

OriginalCalledPartyID --{PARAMETERS-BOUND : bound}-- ::= OCTET STRING (SIZE(
	--bound.&--minOriginalCalledPartyIDLength .. --bound.&--maxOriginalCalledPartyIDLength))
--  Indicates the original called number. Refer to ETSI EN 300 356-1 [23] Original Called Number 
--  for encoding.

PDPID ::= OCTET STRING (SIZE (1))
--	PDP Identifier is a counter used to identify a specific PDP Context within a control
--	relationship between gprsSSF and gsmSCF.

PDPInitiationType ::= ENUMERATED {
	mSInitiated							(0),
	networkInitiated					(1)
	}

QualityOfService ::= SEQUENCE {
	requested-QoS						[0]	GPRS-QoS								OPTIONAL,
	subscribed-QoS						[1]	GPRS-QoS								OPTIONAL,
	negotiated-QoS						[2]	GPRS-QoS								OPTIONAL,
	...
	}
-- The procedure descriptions in clause 11 indicate which one(s) of the
-- QoS variables shall be transported.

ReceivingSideID ::= CHOICE {
	receivingSideID						[1] LegType
	}
-- used to identify LegID in operations sent from gsmSSF to gsmSCF

RedirectingPartyID --{PARAMETERS-BOUND : bound}-- ::= OCTET STRING (SIZE (
	--bound.&--minRedirectingPartyIDLength .. --bound.&--maxRedirectingPartyIDLength))
-- Indicates redirecting number. 
-- Refer to ETSI EN 300 356-1 [23] Redirecting number for encoding.

ReportingConditionUnits ::= CHOICE {
	endOfConnection						[0] IMPLICIT NULL,
	thresholdCountervalue				[1] IMPLICIT INTEGER (SIZE(4))
	}

ReportingConditionEvalue ::= CHOICE {
	occurranceOfEvent					[0] IMPLICIT NULL
	}

RequestedInformationList --{PARAMETERS-BOUND : bound}-- ::= SEQUENCE SIZE (1.. numOfInfoItems) OF RequestedInformation --{bound}--

RequestedInformationTypeList ::= SEQUENCE SIZE (1.. numOfInfoItems) OF RequestedInformationType

RequestedInformation --{PARAMETERS-BOUND : bound}-- ::= SEQUENCE {
	requestedInformationType			[0] RequestedInformationType,
	requestedInformationValue			[1] RequestedInformationValue --{bound}--,
...
	}

RequestedInformationType ::= ENUMERATED {
	callAttemptElapsedTime				(0),
	callStopTime						(1),
	callConnectedElapsedTime			(2),
	releaseCause						(30)
	}

RequestedInformationValue --{PARAMETERS-BOUND : bound}-- ::= CHOICE {
	callAttemptElapsedTimeValue			[0] INTEGER (0..255),
	callStopTimeValue					[1] DateAndTime,
	callConnectedElapsedTimeValue		[2] Integer4,
	releaseCauseValue					[30] Cause --{bound}--
	}
-- The callAttemptElapsedTimeValue is specified in seconds. The unit for the
-- callConnectedElapsedTimeValue is 100 milliseconds

RPCause ::= OCTET STRING (SIZE (1))
-- RP cause according to 3GPP TS 24.011 [10] or 3G TS 29.002 [11].
-- GsmSCF shall send this cause in the ReleaseSMS operation.
-- For a MO-SMS service, the MSC or SGSN shall send the RP Cause to the originating MS.
-- It shall be used to overwrite the RP-Cause element in the RP-ERROR RPDU.
-- For a MT-SMS service, the MSC or SGSN shall send the RP Cause to the sending SMS-GMSC.
-- It shall be used to overwrite the RP-Cause element in the RP-ERROR RPDU.

ScfID --{PARAMETERS-BOUND : bound}-- ::= OCTET STRING (SIZE(
	--bound.&--minScfIDLength .. --bound.&--maxScfIDLength))
-- defined by network operator.
-- Indicates the gsmSCF identity.

SCIBillingChargingCharacteristics  -- {PARAMETERS-BOUND : bound} --  ::= OCTET STRING (SIZE (
     -- bound.& -- minSCIBillingChargingLength.. -- bound.& -- maxSCIBillingChargingLength))
    (CONSTRAINED BY {-- shall be the result of the BER-encoded value of type --
    CAMEL-SCIBillingChargingCharacteristics})
-- Indicates AOC information to be sent to a Mobile Station
-- The violation of the UserDefinedConstraint shall be handled as an ASN.1 syntax error.

SCIGPRSBillingChargingCharacteristics  -- {PARAMETERS-BOUND : bound} --  ::= OCTET STRING (SIZE (
     -- bound.& -- minSCIBillingChargingLength.. -- bound.& -- maxSCIBillingChargingLength))
    (CONSTRAINED BY {-- shall be the result of the BER-encoded value of type -
    CAMEL-SCIGPRSBillingChargingCharacteristics})
-- Indicates AOC information to be sent to a Mobile Station
-- The violation of the UserDefinedConstraint shall be handled as an ASN.1 syntax error.

SendingSideID ::= CHOICE {sendingSideID [0] LegType}
-- used to identify LegID in operations sent from gsmSCF to gsmSSF

ServiceInteractionIndicatorsTwo ::= SEQUENCE {
	forwardServiceInteractionInd		[0]	ForwardServiceInteractionInd			OPTIONAL,
	-- applicable to operations InitialDP, Connect and ContinueWithArgument.
	backwardServiceInteractionInd		[1]	BackwardServiceInteractionInd			OPTIONAL,
	-- applicable to operations Connect and ContinueWithArgument.
	bothwayThroughConnectionInd			[2] BothwayThroughConnectionInd				OPTIONAL,
	-- applicable to ConnectToResource and EstablishTemporaryConnection
	connectedNumberTreatmentInd			[4]	ConnectedNumberTreatmentInd				OPTIONAL,
	-- applicable to Connect and ContinueWithArgument
	nonCUGCall							[13] NULL									OPTIONAL,
	-- applicable to Connect and ContinueWithArgument
	-- indicates that no parameters for CUG shall be used for the call (i.e. the call shall 
	-- be a non-CUG call). 
	-- If not present, it indicates one of three things:
	--  a) continue with modified CUG information (when one or more of either CUG Interlock Code 
	--     and Outgoing Access Indicator are present), or
	--  b) continue with original CUG information (when neither CUG Interlock Code or Outgoing 
	--     Access Indicator are present), i.e. no IN impact.
	--  c) continue with the original non-CUG call.
	holdTreatmentIndicator				[50] OCTET STRING (SIZE(1))					OPTIONAL,
	-- applicable to InitialDP, Connect and ContinueWithArgument
	-- acceptHoldRequest	'xxxx xx01'B
	-- rejectHoldRequest	'xxxx xx10'B
	-- if absent from Connect or ContinueWithArgument,
	-- then CAMEL service does not affect call hold treatment
	cwTreatmentIndicator				[51] OCTET STRING (SIZE(1))					OPTIONAL,
	-- applicable to InitialDP, Connect and ContinueWithArgument
	-- acceptCw	'xxxx xx01'B
	-- rejectCw	'xxxx xx10'B
	-- if absent from Connect or ContinueWithArgument,
	-- then CAMEL service does not affect call waiting treatment
	ectTreatmentIndicator				[52] OCTET STRING (SIZE(1))					OPTIONAL,
	-- applicable to InitialDP, Connect and ContinueWithArgument
	-- acceptEctRequest	'xxxx xx01'B
	-- rejectEctRequest	'xxxx xx10'B
	-- if absent from Connect or ContinueWithArgument,
	-- then CAMEL service does not affect explicit call transfer treatment
	...
	}

SGSNCapabilities ::= OCTET STRING (SIZE (1))

--  Indicates the SGSN capabilities. The coding of the parameter is as follows:
--  Bit	Value				Meaning
--  0	0					AoC not supported by SGSN
--		1					AoC supported by SGSN 
--  1	-					This bit is reserved in CAP V.3
--  2	-					This bit is reserved in CAP V.3
--  3	-					This bit is reserved in CAP V.3
--  4	-					This bit is reserved in CAP V.3
--  5	-					This bit is reserved in CAP V.3
--  6	-					This bit is reserved in CAP V.3
--  7	-					This bit is reserved in CAP V.3

SMSEvent ::= SEQUENCE {
	eventTypeSMS						[0] EventTypeSMS,
	monitorMode							[1] MonitorMode
	}

TariffSwitchInterval ::= INTEGER (1 .. 86400)
-- TariffSwitchInterval is measured in 1 second units

TimeAndTimezone --{PARAMETERS-BOUND : bound}-- ::= OCTET STRING (SIZE(
	--bound.&--minTimeAndTimezoneLength .. --bound.&--maxTimeAndTimezoneLength))
--  Indicates the time and timezone, relative to GMT. This parameter BCD encoded. 
--  The year digit indicating millenium occupies bits 0-3 of the first octet, and the year 
--  digit indicating century occupies bits 4-7 of the first octet. 
--  The year digit indicating decade occupies bits 0-3 of the second octet, whilst the digit 
--  indicating the year within the decade occupies bits 4-7 of the second octet. 
--  The most significant month digit occupies bits 0-3 of the third octet, and the least 
--  significant month digit occupies bits 4-7 of the third octet. 
--  The most significant day digit occupies bits 0-3 of the fourth octet, and the least 
--  significant day digit occupies bits 4-7 of the fourth octet. 
--  The most significant hours digit occupies bits 0-3 of the fifth octet, and the least 
--  significant hours digit occupies bits 4-7 of the fifth octet. 
--  The most significant minutes digit occupies bits 0-3 of the sixth octet, and the least 
--  significant minutes digit occupies bits 4-7 of the sixth octet. 
--  The most significant seconds digit occupies bits 0-3 of the seventh octet, and the least 
--  significant seconds digit occupies bits 4-7 of the seventh octet.
--
--  The timezone information occupies the eighth octet. For the encoding of Timezone refer to 
--  3GPP TS 23.040 [6].
--
--  The BCD digits are packed and encoded as follows:
--
--  Bit	 7  6  5   4  |  3  2  1  0 
--       2nd digit    | 1st digit          Octet 1
--       3rd digit    | 4th digit          Octet 2
--           	         ..                   ..
--       nth digit    | n-1th digit        Octet m
--
--       0000		digit 0
--       0001		digit 1
--       0010		digit 2
--       0011		digit 3
--       0100		digit 4
--       0101		digit 5
--       0110		digit 6
--       0111		digit 7
--       1000		digit 8
--       1001		digit 9
--       1010		spare
--       1011		spare
--       1100		spare
--       1101		spare
--       1110		spare
--       1101		spare
--
-- where the leftmost bit of the digit is either bit 7 or bit 3 of the octet.

TimeIfNoTariffSwitch ::= INTEGER(0..864000)
-- TimeIfNoTariffSwitch is measured in 100 millisecond intervals

TimeIfTariffSwitch ::= SEQUENCE {
	timeSinceTariffSwitch				[0] INTEGER(0..864000),
	tariffSwitchInterval				[1] INTEGER(1..864000)						OPTIONAL
	}
-- timeSinceTariffSwitch and tariffSwitchInterval are measured in 100 millisecond intervals

TimeInformation ::= CHOICE {
	timeIfNoTariffSwitch				[0] TimeIfNoTariffSwitch,
	timeIfTariffSwitch					[1] TimeIfTariffSwitch
	}
-- Indicates call duration information

TimerID ::= ENUMERATED {
	tssf								(0)
	}
-- Indicates the timer to be reset.

TimerValue ::= Integer4
-- Indicates the timer value (in seconds).

Tone ::= SEQUENCE {
	toneID								[0] Integer4,
	duration							[1] Integer4								OPTIONAL,
...
	}
-- The duration specifies the length of the tone in seconds, value 0 indicates infinite duration.

TPDataCodingScheme ::= OCTET STRING (SIZE (1))
-- TP Data Coding Scheme according to 3GPP TS 23.040 [6]

TPProtocolIdentifier ::= OCTET STRING (SIZE (1))
-- indicates the protocol used above the SM-Transfer Layer as specified in 3GPP TS 23.040 [6].

TPShortMessageSpecificInfo ::= OCTET STRING (SIZE (1))
-- contains the 1st octect of the applicable TPDU or the SMS-COMMAND TPDU as specified in
-- 3GPP TS 23.040 [6].

TPValidityPeriod ::= OCTET STRING (SIZE (1..7))
-- indicates the length of the validity period or the absolute time of the validity 
-- period termination as specified in 3GPP TS 23.040 [6].
-- the length of ValidityPeriod is either 1 octet or 7 octets

TransferredVolume ::= CHOICE {
	volumeIfNoTariffSwitch				[0] INTEGER (0..4294967295),
	volumeIfTariffSwitch 				[1] SEQUENCE {
		volumeSinceLastTariffSwitch			[0]	INTEGER (0..4294967295),
		volumeTariffSwitchInterval			[1]	INTEGER (0..4294967295)				OPTIONAL
		}
	}
--	volumeIfNoTariffSwitch, volumeSinceLastTariffSwitch and volumeTariffSwitchInterval
--	are measured in bytes.

TransferredVolumeRollOver ::= CHOICE {
	rO-VolumeIfNoTariffSwitch			[0] INTEGER (0..255),
	rO-VolumeIfTariffSwitch				[1] SEQUENCE {
		rO-VolumeSinceLastTariffSwitch		[0]	INTEGER (0..255)					OPTIONAL,
		rO-VolumeTariffSwitchInterval		[1]	INTEGER (0..255)					OPTIONAL
		}
	}
--	rO-VolumeIfNoTariffSwitch, rO-VolumeSinceLastTariffSwitch and rO-VolumeTariffSwitchInterval
--	present counters indicating the number of parameter range rollovers.

UnavailableNetworkResource ::= ENUMERATED {
	unavailableResources				(0),
	componentFailure					(1),
	basicCallProcessingException		(2),
	resourceStatusFailure				(3),
	endUserFailure						(4)
	}
-- Indicates the network resource that failed.

Units ::= INTEGER (1 .. 10000)

VariablePart --{PARAMETERS-BOUND : bound}-- ::= CHOICE {
	integer								[0] Integer4,
	number								[1] Digits --{bound}--,	-- Generic digits
	time								[2] OCTET STRING (SIZE(2)),	-- HH: MM, BCD coded
	date								[3] OCTET STRING (SIZE(4)),	-- YYYYMMDD, BCD coded
	price								[4] OCTET STRING (SIZE(4))
	}
--  Indicates the variable part of the message. Time is BCD encoded. 
--  The most significant hours digit occupies bits 0-3 of the first octet, and the least 
--  significant digit occupies bits 4-7 of the first octet. The most significant minutes digit 
--  occupies bits 0-3 of the second octet, and the least significant digit occupies bits 4-7 
--  of the second octet. 
--
--  Date is BCD encoded. The year digit indicating millenium occupies bits 0-3 of the first octet, 
--  and the year digit indicating century occupies bits 4-7 of the first octet. The year digit 
--  indicating decade occupies bits 0-3 of the second octet, whilst the digit indicating the year 
--  within the decade occupies bits 4-7 of the second octet.
--  The most significant month digit occupies bits 0-3 of the third octet, and the least 
--  significant month digit occupies bits 4-7 of the third octet. The most significant day digit 
--  occupies bits 0-3 of the fourth octet, and the least significant day digit occupies bits 4-7 
--  of the fourth octet.
--  Price is BCD encoded. The digit indicating hundreds of thousands occupies bits 0-3 of the 
--  first octet, and the digit indicating tens of thousands occupies bits 4-7 of the first octet.
--  The digit indicating thousands occupies bits 0-3 of the second octet, whilst the digit 
--  indicating hundreds occupies bits 4-7 of the second octet. The digit indicating tens occupies 
--  bits 0-3 of the third octet, and the digit indicating 0 to 9 occupies bits 4-7 of the third 
--  octet. The tenths digit occupies bits 0-3 of the fourth octet, and the hundredths digit 
--  occupies bits 4-7 of the fourth octet.
--
--  For the encoding of digits in an octet, refer to the timeAndtimezone parameter

-- The Definition of range of constants follows
numOfInfoItems INTEGER ::= 4

--not used 
--not used END
--not used 

--------------------------------------------------------------------------------
--------------------------------------------------------------------------------
--------------------------------------------------------------------------------


-- Module ----------------------------------------------------------------------
--------------------------------------------------------------------------------
-- CAP Error Types.
--------------------------------------------------------------------------------
--------------------------------------------------------------------------------

--errortypes {itu-t(0) identified-organization(4) etsi(0) mobileDomain(0) umts-network(1) modules(3) cap-errortypes(51) version4(3)}
-- This module contains the type definitions for the CAP Error Types.
-- Where a parameter of type CHOICE is tagged with a specific tag value, the tag is automatically 
-- replaced with an EXPLICIT tag of the same value.


--not used 
--not used canceled ERROR              ::= {
--not used     CODE    errcode-canceled
--not used     }
-- The operation has been canceled.
--not used 
--not used cancelFailed ERROR          ::= {
--not used     PARAMETER   SEQUENCE {

CancelFailed ::= SEQUENCE {
        problem                 [0] ENUMERATED {
            unknownOperation        (0),
            tooLate                 (1),
            operationNotCancellable (2)
            },
        operation               [1] InvokeID,
        ...
        }

-- The operation failed to be canceled.

--not used     CODE    errcode-cancelFailed
--not used     }
-- The operation failed to be canceled.
--not used 
--not used eTCFailed ERROR             ::= {
--not used     CODE    errcode-eTCFailed
--not used     }
-- The establish temporary connection failed.
--not used 
--not used improperCallerResponse ERROR ::= {
--not used     CODE    errcode-improperCallerResponse
--not used     }
-- The caller response was not as expected.
--not used 
--not used missingCustomerRecord ERROR ::= {
--not used     CODE    errcode-missingCustomerRecord
--not used     }
-- The Service Logic Program could not be found in the gsmSCF.
--not used 
--not used missingParameter ERROR      ::= {
--not used     CODE    errcode-missingParameter
--not used     }
-- An expected optional parameter was not received.
--not used 
--not used parameterOutOfRange ERROR   ::= {
--not used     CODE    errcode-parameterOutOfRange
--not used     }
-- The parameter was not as expected (e.g. missing or out of range).
--not used 
--not used requestedInfoError ERROR    ::= {
--not used     PARAMETER    ENUMERATED {

RequestedInfoError ::= ENUMERATED {
            unknownRequestedInfo        (1),
            requestedInfoNotAvailable   (2)
            -- other values FOR FURTHER STUDY
            }

-- The requested information cannot be found.

--not used     CODE    errcode-requestedInfoError
--not used     }
-- The requested information cannot be found.
--not used 
--not used systemFailure ERROR         ::= {
--not used     PARAMETER   UnavailableNetworkResource
--not used     CODE    errcode-systemFailure
--not used     }
-- The operation could not be completed due to a system failure at the serving physical entity.
--not used 
--not used taskRefused ERROR           ::= {
--not used     PARAMETER   ENUMERATED {

TaskRefused ::= ENUMERATED {
            generic                     (0),
            unobtainable                (1),
            congestion                  (2)
            -- other values FOR FURTHER STUDY
            }

-- An entity normally capable of the task requested cannot or chooses not to perform the task at 
-- this time. This includes error situations like congestion and unobtainable address as used in 
-- e.g. the connect operation.)

--not used 
--not used     CODE    errcode-taskRefused
--not used     }
-- An entity normally capable of the task requested cannot or chooses not to perform the task at 
-- this time. This includes error situations like congestion and unobtainable address as used in 
-- e.g. the connect operation.)
--not used 
--not used unavailableResource ERROR   ::= {
--not used     CODE    errcode-unavailableResource
--not used     }
-- A requested resource is not available at the serving entity.
--not used 
--not used unexpectedComponentSequence ERROR ::= {
--not used     CODE    errcode-unexpectedComponentSequence
--not used     }
-- An incorrect sequence of Components was received (e.g."DisconnectForwardConnection" 
-- followed by"PlayAnnouncement").
--not used 
--not used unexpectedDataValue ERROR ::= {
--not used     CODE    errcode-unexpectedDataValue
--not used     }
-- The data value was not as expected (e.g. routing number expected but billing number received)
--not used 
--not used unexpectedParameter ERROR ::= {
--not used     CODE    errcode-unexpectedParameter
--not used     }
-- A parameter received was not expected.
--not used 
--not used unknownLegID ERROR      ::= {
--not used     CODE    errcode-unknownLegID
--not used     }
-- Leg not known to the gsmSSF.
--not used 
--not used unknownPDPID ERROR      ::= {
--not used     CODE    errcode-unknownPDPID
--not used     }
-- PDPID not known by the receiving entity.
--not used 
--not used unknownGPRSReference ERROR      ::= {
--not used     CODE    errcode-unknownGPRSREference
--not used     }
-- GPRS Reference not known by the receiving entity.
--not used 
--not used overlappingDialogue ERROR       ::= {
--not used     CODE    errcode-overlappingDialogue
--not used     }
-- A dialogue exists already for the same relationship.
--not used 
--not used END
--not used 

--------------------------------------------------------------------------------
--------------------------------------------------------------------------------
--------------------------------------------------------------------------------


-- Module ----------------------------------------------------------------------
--------------------------------------------------------------------------------
-- CAP Operation Codes.
--------------------------------------------------------------------------------
--------------------------------------------------------------------------------


--------------------------------------------------------------------------------
--------------------------------------------------------------------------------
--------------------------------------------------------------------------------


-- Module ----------------------------------------------------------------------
--------------------------------------------------------------------------------
-- CAP Error Codes.
--------------------------------------------------------------------------------
--------------------------------------------------------------------------------


-- Module ----------------------------------------------------------------------
--------------------------------------------------------------------------------
-- CAP Classes.
--------------------------------------------------------------------------------
--------------------------------------------------------------------------------

--not impl CAP-classes {ccitt(0) identified-organization(4) etsi(0) mobileDomain(0) umts-network(1)
--not impl modules(3) cAP-classes(54) version3(2)}
--not impl 
--not impl DEFINITIONS ::= BEGIN
--not impl 
--not impl IMPORTS
--not impl 
--not impl ROS-OBJECT-CLASS,
--not impl CONTRACT,
--not impl OPERATION-PACKAGE,
--not impl Code,
--not impl OPERATION 
--not impl FROM Remote-Operations-Information-Objects ros-InformationObjects
--not impl 
--not impl     emptyBind,
--not impl     emptyUnbind
--not impl FROM Remote-Operations-Useful-Definitions ros-UsefulDefinitions
--not impl 
--not impl     id-rosObject-gsmSRF,
--not impl     id-rosObject-gsmSSF,
--not impl     ros-InformationObjects,
--not impl     ros-UsefulDefinitions,
--not impl     gsmSSF-gsmSCF-Protocol,
--not impl     gsmSCF-gsmSRF-Protocol,
--not impl     datatypes
--not impl FROM CAP-object-identifiers {ccitt(0) identified-organization(4) etsi(0) mobileDomain(0)
--not impl umts-network(1) modules(3) cAP-object-identifiers(17) version3(2)}
--not impl 
--not impl     capSsfToScfGeneric,
--not impl     capAssistHandoffssfToScf
--not impl FROM CAP-gsmSSF-gsmSCF-pkgs-contracts-acs gsmSSF-gsmSCF-Protocol
--not impl 
--not impl     gsmSRF-gsmSCF-contract
--not impl FROM CAP-gsmSCF-gsmSRF-pkgs-contracts-acs gsmSCF-gsmSRF-Protocol
--not impl 
--not impl     CriticalityType
--not impl FROM CAP-datatypes datatypes
--not impl 
--not impl ;
--not impl 
--not impl gsmSSF ROS-OBJECT-CLASS ::= {
--not impl     INITIATES   {capSsfToScfGeneric|
--not impl                 capAssistHandoffssfToScf}
--not impl     RESPONDS    {capSsfToScfGeneric}
--not impl     ID          id-rosObject-gsmSSF
--not impl     }
--not impl 
--not impl gsmSRF ROS-OBJECT-CLASS ::= {
--not impl     INITIATES   {gsmSRF-gsmSCF-contract} 
--not impl     ID          id-rosObject-gsmSRF
--not impl     }
--not impl 
--not impl EXTENSION ::= CLASS {
--not impl     &ExtensionType,
--not impl     &criticality    CriticalityType DEFAULT ignore,
--not impl     &id Code
--not impl     }
--not impl 
--not impl WITH SYNTAX {
--not impl     EXTENSION-SYNTAX    &ExtensionType
--not impl     CRITICALITY         &criticality
--not impl     IDENTIFIED BY       &id
--not impl     }
-- Example of addition of an extension named 'Some Network Specific Indicator' of type
-- BOOLEAN, with criticality 'abort' and to be identified as extension number 1
-- Example of definition using the above information object class: 
--
-- SomeNetworkSpecificIndicator EXTENSION ::= {
--  EXTENSION-SYNTAX    BOOLEAN
--  CRITICALITY         abort
--  IDENTIFIED BY       local: 1
--  }

-- Example of transfer syntax, using the ExtensionField datatype as specified in subclause 5.
-- Assuming the value of the extension is set to TRUE, the extensions parameter
-- becomes a Sequence of type INTEGER ::= 1, criticality ENUMERATED ::= 1 and value [1]
-- EXPLICIT BOOLEAN ::= TRUE.
--
-- Use of Q.1400 [28] defined Extension is for further study.
-- In addition the extension mechanism marker is used to identify the future minor additions
-- to CAP.
--not impl 
--not impl firstExtension EXTENSION ::= {
--not impl     EXTENSION-SYNTAX    NULL
--not impl     CRITICALITY         ignore
--not impl     IDENTIFIED BY       local: 1
--not impl     }
-- firstExtension is just an example.
--not impl 
--not impl SupportedExtensions {PARAMETERS-BOUND : bound} EXTENSION ::= {firstExtension, ...
-- full set of network operator extensions --
--not impl }
-- SupportedExtension is the full set of the network operator extensions.
--not impl 
--not impl PARAMETERS-BOUND ::= CLASS
--not impl {
--not impl     &minAccessPointNameLength                   INTEGER,
--not impl     &maxAccessPointNameLength                   INTEGER,
--not impl     &minAChBillingChargingLength                INTEGER,
--not impl     &maxAChBillingChargingLength                INTEGER,
--not impl     &minAttributesLength                        INTEGER,
--not impl     &maxAttributesLength                        INTEGER,
--not impl     &maxBearerCapabilityLength                  INTEGER,
--not impl     &minCalledPartyBCDNumberLength              INTEGER,
--not impl     &maxCalledPartyBCDNumberLength              INTEGER,
--not impl     &minCalledPartyNumberLength                 INTEGER,
--not impl     &maxCalledPartyNumberLength                 INTEGER,
--not impl     &minCallingPartyNumberLength                INTEGER,
--not impl     &maxCallingPartyNumberLength                INTEGER,
--not impl     &minCallResultLength                        INTEGER,
--not impl     &maxCallResultLength                        INTEGER,
--not impl     &maxCauseLength                             INTEGER,
--not impl     &minDigitsLength                            INTEGER,
--not impl     &maxDigitsLength                            INTEGER,
--not impl     &minFCIBillingChargingDataLength            INTEGER,
--not impl     &maxFCIBillingChargingDataLength            INTEGER,
--not impl     &minFCIBillingChargingLength                INTEGER,
--not impl     &maxFCIBillingChargingLength                INTEGER,
--not impl     &minGenericNumberLength                     INTEGER,
--not impl     &maxGenericNumberLength                     INTEGER,
--not impl     &minIPSSPCapabilitiesLength                 INTEGER,
--not impl     &maxIPSSPCapabilitiesLength                 INTEGER,
--not impl     &minLocationNumberLength                    INTEGER,
--not impl     &maxLocationNumberLength                    INTEGER,
--not impl     &minMessageContentLength                    INTEGER,
--not impl     &maxMessageContentLength                    INTEGER,
--not impl     &minOriginalCalledPartyIDLength             INTEGER,
--not impl     &maxOriginalCalledPartyIDLength             INTEGER,
--not impl     &minRedirectingPartyIDLength                INTEGER,
--not impl     &maxRedirectingPartyIDLength                INTEGER,
--not impl     &minScfIDLength                             INTEGER,
--not impl     &maxScfIDLength                             INTEGER,
--not impl     &minSCIBillingChargingLength                INTEGER,
--not impl     &maxSCIBillingChargingLength                INTEGER,
--not impl     &minTimeAndTimezoneLength                   INTEGER,
--not impl     &maxTimeAndTimezoneLength                   INTEGER,
--not impl     &numOfBCSMEvents                            INTEGER,
--not impl     &numOfSMSEvents                             INTEGER,
--not impl     &numOfGPRSEvents                            INTEGER,
--not impl     &numOfExtensions                            INTEGER,
--not impl     &numOfGenericNumbers                        INTEGER,
--not impl     &numOfMessageIDs                            INTEGER
--not impl }
--not impl 
--not impl WITH SYNTAX
--not impl {
--not impl     MINIMUM-FOR-ACCESS-POINT-NAME               &minAccessPointNameLength
--not impl     MAXIMUM-FOR-ACCESS-POINT-NAME               &maxAccessPointNameLength
--not impl     MINIMUM-FOR-ACH-BILLING-CHARGING            &minAChBillingChargingLength
--not impl     MAXIMUM-FOR-ACH-BILLING-CHARGING            &maxAChBillingChargingLength
--not impl     MINIMUM-FOR-ATTRIBUTES                      &minAttributesLength
--not impl     MAXIMUM-FOR-ATTRIBUTES                      &maxAttributesLength
--not impl     MAXIMUM-FOR-BEARER-CAPABILITY               &maxBearerCapabilityLength
--not impl     MINIMUM-FOR-CALLED-PARTY-BCD-NUMBER         &minCalledPartyBCDNumberLength
--not impl     MAXIMUM-FOR-CALLED-PARTY-BCD-NUMBER         &maxCalledPartyBCDNumberLength
--not impl     MINIMUM-FOR-CALLED-PARTY-NUMBER             &minCalledPartyNumberLength
--not impl     MAXIMUM-FOR-CALLED-PARTY-NUMBER             &maxCalledPartyNumberLength
--not impl     MINIMUM-FOR-CALLING-PARTY-NUMBER            &minCallingPartyNumberLength
--not impl     MAXIMUM-FOR-CALLING-PARTY-NUMBER            &maxCallingPartyNumberLength
--not impl     MINIMUM-FOR-CALL-RESULT                     &minCallResultLength
--not impl     MAXIMUM-FOR-CALL-RESULT                     &maxCallResultLength
--not impl     MAXIMUM-FOR-CAUSE                           &maxCauseLength
--not impl     MINIMUM-FOR-DIGITS                          &minDigitsLength
--not impl     MAXIMUM-FOR-DIGITS                          &maxDigitsLength
--not impl     MINIMUM-FOR-FCI-BILLING-CHARGING-DATA       &minFCIBillingChargingDataLength
--not impl     MAXIMUM-FOR-FCI-BILLING-CHARGING-DATA       &maxFCIBillingChargingDataLength
--not impl     MINIMUM-FOR-FCI-BILLING-CHARGING            &minFCIBillingChargingLength
--not impl     MAXIMUM-FOR-FCI-BILLING-CHARGING            &maxFCIBillingChargingLength
--not impl     MINIMUM-FOR-GENERIC-NUMBER                  &minGenericNumberLength
--not impl     MAXIMUM-FOR-GENERIC-NUMBER                  &maxGenericNumberLength
--not impl     MINIMUM-FOR-IP-SSP-CAPABILITIES             &minIPSSPCapabilitiesLength
--not impl     MAXIMUM-FOR-IP-SSP-CAPABILITIES             &maxIPSSPCapabilitiesLength
--not impl     MINIMUM-FOR-LOCATION-NUMBER                 &minLocationNumberLength
--not impl     MAXIMUM-FOR-LOCATION-NUMBER                 &maxLocationNumberLength
--not impl     MINIMUM-FOR-MESSAGE-CONTENT                 &minMessageContentLength
--not impl     MAXIMUM-FOR-MESSAGE-CONTENT                 &maxMessageContentLength
--not impl     MINIMUM-FOR-ORIGINAL-CALLED-PARTY-ID        &minOriginalCalledPartyIDLength
--not impl     MAXIMUM-FOR-ORIGINAL-CALLED-PARTY-ID        &maxOriginalCalledPartyIDLength
--not impl     MINIMUM-FOR-REDIRECTING-ID                  &minRedirectingPartyIDLength
--not impl     MAXIMUM-FOR-REDIRECTING-ID                  &maxRedirectingPartyIDLength
--not impl     MINIMUM-FOR-GSMSCF-ID                       &minScfIDLength
--not impl     MAXIMUM-FOR-GSMSCF-ID                       &maxScfIDLength
--not impl     MINIMUM-FOR-SCI-BILLING-CHARGING            &minSCIBillingChargingLength
--not impl     MAXIMUM-FOR-SCI-BILLING-CHARGING            &maxSCIBillingChargingLength
--not impl     MINIMUM-FOR-TIME-AND-TIMEZONE               &minTimeAndTimezoneLength
--not impl     MAXIMUM-FOR-TIME-AND-TIMEZONE               &maxTimeAndTimezoneLength 
--not impl     NUM-OF-BCSM-EVENT                           &numOfBCSMEvents
--not impl     NUM-OF-SMS-EVENTS                           &numOfSMSEvents
--not impl     NUM-OF-GPRS-EVENTS                          &numOfGPRSEvents
--not impl     NUM-OF-EXTENSIONS                           &numOfExtensions
--not impl     NUM-OF-GENERIC-NUMBERS                      &numOfGenericNumbers
--not impl     NUM-OF-MESSAGE-IDS                          &numOfMessageIDs
--not impl }
--not impl 
--not impl 
--not impl networkSpecificBoundSet PARAMETERS-BOUND ::=
--not impl {
--not impl     MINIMUM-FOR-ACCESS-POINT-NAME               2
--not impl     MAXIMUM-FOR-ACCESS-POINT-NAME               10
--not impl     MINIMUM-FOR-ACH-BILLING-CHARGING            5   
--not impl     MAXIMUM-FOR-ACH-BILLING-CHARGING            177
--not impl     MINIMUM-FOR-ATTRIBUTES                      2
--not impl     MAXIMUM-FOR-ATTRIBUTES                      10
--not impl     MAXIMUM-FOR-BEARER-CAPABILITY               11
--not impl     MINIMUM-FOR-CALLED-PARTY-BCD-NUMBER         1
--not impl     MAXIMUM-FOR-CALLED-PARTY-BCD-NUMBER         41
--not impl     MINIMUM-FOR-CALLED-PARTY-NUMBER             3
--not impl     MAXIMUM-FOR-CALLED-PARTY-NUMBER             18
--not impl     MINIMUM-FOR-CALLING-PARTY-NUMBER            2
--not impl     MAXIMUM-FOR-CALLING-PARTY-NUMBER            10
--not impl     MINIMUM-FOR-CALL-RESULT                     12
--not impl     MAXIMUM-FOR-CALL-RESULT                     24
--not impl     MAXIMUM-FOR-CAUSE                           2
--not impl     MINIMUM-FOR-DIGITS                          2
--not impl     MAXIMUM-FOR-DIGITS                          16
--not impl     MINIMUM-FOR-FCI-BILLING-CHARGING-DATA       1
--not impl     MAXIMUM-FOR-FCI-BILLING-CHARGING-DATA       160
--not impl     MINIMUM-FOR-FCI-BILLING-CHARGING            5
--not impl     MAXIMUM-FOR-FCI-BILLING-CHARGING            172
--not impl     MINIMUM-FOR-GENERIC-NUMBER                  3
--not impl     MAXIMUM-FOR-GENERIC-NUMBER                  11
--not impl     MINIMUM-FOR-IP-SSP-CAPABILITIES             1
--not impl     MAXIMUM-FOR-IP-SSP-CAPABILITIES             4
--not impl     MINIMUM-FOR-LOCATION-NUMBER                 2
--not impl     MAXIMUM-FOR-LOCATION-NUMBER                 10
--not impl     MINIMUM-FOR-MESSAGE-CONTENT                 1
--not impl     MAXIMUM-FOR-MESSAGE-CONTENT                 127
--not impl     MINIMUM-FOR-ORIGINAL-CALLED-PARTY-ID        2
--not impl     MAXIMUM-FOR-ORIGINAL-CALLED-PARTY-ID        10
--not impl     MINIMUM-FOR-REDIRECTING-ID                  2
--not impl     MAXIMUM-FOR-REDIRECTING-ID                  10
--not impl     MINIMUM-FOR-GSMSCF-ID                       2
--not impl     MAXIMUM-FOR-GSMSCF-ID                       10
--not impl     MINIMUM-FOR-SCI-BILLING-CHARGING            4
--not impl     MAXIMUM-FOR-SCI-BILLING-CHARGING            69
--not impl     MINIMUM-FOR-TIME-AND-TIMEZONE               8
--not impl     MAXIMUM-FOR-TIME-AND-TIMEZONE               8
--not impl     NUM-OF-BCSM-EVENT                           10
--not impl     NUM-OF-SMS-EVENTS                           10
--not impl     NUM-OF-GPRS-EVENTS                          10
--not impl     NUM-OF-EXTENSIONS                           10
--not impl     NUM-OF-GENERIC-NUMBERS                      5
--not impl     NUM-OF-MESSAGE-IDS                          16
--not impl }
--not impl 
--not impl END
--not impl 


----------------------------------------------------------------------------
-- Replacement for object networkSpecificBoundSet of class PARAMETERS-BOUND.
----------------------------------------------------------------------------
minAccessPointNameLength            INTEGER ::= 2    
maxAccessPointNameLength            INTEGER ::= 10    
minAChBillingChargingLength         INTEGER ::= 5    
maxAChBillingChargingLength         INTEGER ::= 177    
minAttributesLength                 INTEGER ::= 2    
maxAttributesLength                 INTEGER ::= 10    
maxBearerCapabilityLength           INTEGER ::= 11    
minCalledPartyBCDNumberLength       INTEGER ::= 1    
maxCalledPartyBCDNumberLength       INTEGER ::= 41    
minCalledPartyNumberLength          INTEGER ::= 3    
maxCalledPartyNumberLength          INTEGER ::= 18    
minCallingPartyNumberLength         INTEGER ::= 2    
maxCallingPartyNumberLength         INTEGER ::= 10    
minCallResultLength                 INTEGER ::= 12    
maxCallResultLength                 INTEGER ::= 24    
maxCauseLength                      INTEGER ::= 2    
minDigitsLength                     INTEGER ::= 2    
maxDigitsLength                     INTEGER ::= 16    
minFCIBillingChargingDataLength     INTEGER ::= 1    
maxFCIBillingChargingDataLength     INTEGER ::= 160    
minFCIBillingChargingLength         INTEGER ::= 5    
maxFCIBillingChargingLength         INTEGER ::= 172    
minGenericNumberLength              INTEGER ::= 3    
maxGenericNumberLength              INTEGER ::= 11    
minIPSSPCapabilitiesLength          INTEGER ::= 1    
maxIPSSPCapabilitiesLength          INTEGER ::= 4    
minLocationNumberLength             INTEGER ::= 2    
maxLocationNumberLength             INTEGER ::= 10    
minMessageContentLength             INTEGER ::= 1    
maxMessageContentLength             INTEGER ::= 127    
minOriginalCalledPartyIDLength      INTEGER ::= 2    
maxOriginalCalledPartyIDLength      INTEGER ::= 10    
minRedirectingPartyIDLength         INTEGER ::= 2    
maxRedirectingPartyIDLength         INTEGER ::= 10    
minScfIDLength                      INTEGER ::= 2    
maxScfIDLength                      INTEGER ::= 10    
minSCIBillingChargingLength         INTEGER ::= 4    
maxSCIBillingChargingLength         INTEGER ::= 69    
minTimeAndTimezoneLength            INTEGER ::= 8    
maxTimeAndTimezoneLength            INTEGER ::= 8    
numOfBCSMEvents                     INTEGER ::= 10    
numOfSMSEvents                      INTEGER ::= 10    
numOfGPRSEvents                     INTEGER ::= 10    
numOfExtensions                     INTEGER ::= 10    
numOfGenericNumbers                 INTEGER ::= 5    
numOfMessageIDs                     INTEGER ::= 16    
minCarrierLength					INTEGER	::= 4 
maxCarrierLength					INTEGER	::= 4 
minCauseLength 						INTEGER	::= 2 
minGPRSCauseLength 					INTEGER	::= 1 
maxGPRSCauseLength 					INTEGER	::= 1 
--minLocationNumberLength				INTEGER	::= 2 
--maxLocationNumberLength 			INTEGER	::= 10 
minPDPAddressLength 				INTEGER	::= 1 
maxPDPAddressLength 				INTEGER	::= 63 
--numOfCSs 							INTEGER	::= 67 
minComponentLength					INTEGER	::= 1
maxComponentLength					INTEGER	::= 2

--------------------------------------------------------------------------------
--------------------------------------------------------------------------------
--------------------------------------------------------------------------------


-- Module ----------------------------------------------------------------------
--------------------------------------------------------------------------------
-- CAP Object Identifiers (IDs).
--------------------------------------------------------------------------------
--------------------------------------------------------------------------------

--------------------------------------------------------------------------------
--------------------------------------------------------------------------------
--------------------------------------------------------------------------------


-- Module ----------------------------------------------------------------------
--------------------------------------------------------------------------------
-- CAP Object Identifiers (IDs).
--------------------------------------------------------------------------------
--------------------------------------------------------------------------------

--not impl CAP-object-identifiers {ccitt(0) identified-organization(4) etsi(0) mobileDomain(0) umts-network(1) modules(3) cAP-object-identifiers(17) version3(2)}
--not impl 
--not impl 
--not impl DEFINITIONS ::= BEGIN
--not impl 
-- This module assigns object identifiers for Modules, Packages, Contracts and AC 
-- for CAP
--not impl 
-- For Modules from TCAP, ROS, 
--not impl tc-Messages                     OBJECT IDENTIFIER ::=   
--not impl     {ccitt  recommendation q 773 modules(2) messages(1) version3(3)}
--not impl tc-NotationExtensions           OBJECT IDENTIFIER ::=   
--not impl     {ccitt  recommendation q 775 modules(2) notation-extension (4) version1(1)}
--not impl ros-InformationObjects          OBJECT IDENTIFIER ::=   
--not impl     {joint-iso-ccitt remote-operations(4) informationObjects(5) version1(0)}
--not impl ros-genericPDUs                 OBJECT IDENTIFIER ::=   
--not impl     {joint-iso-ccitt remote-operations(4) generic-ROS-PDUs(6) version1(0)}
--not impl ros-UsefulDefinitions           OBJECT IDENTIFIER ::=   
--not impl     {joint-iso-ccitt remote-operations(4) useful-definitions(7) version1(0)}
--not impl sese-APDUs                      OBJECT IDENTIFIER ::=   
--not impl     {joint-iso-ccitt genericULS(20) modules(1) seseAPDUs(6)}
--not impl guls-Notation                   OBJECT IDENTIFIER ::=   
--not impl     {joint-iso-ccitt genericULS (20) modules (1) notation (1)}
--not impl guls-SecurityTransformations    OBJECT IDENTIFIER ::=   
--not impl     {joint-iso-ccitt genericULS (20) modules (1) gulsSecurityTransformations (3)}
--not impl ds-UsefulDefinitions            OBJECT IDENTIFIER ::=   
--not impl     {joint-iso-ccitt ds(5) module(1) usefulDefinitions(0) 3}
--not impl spkmGssTokens                   OBJECT IDENTIFIER ::=   
--not impl     {iso(1) identified-organization(3) dod(6) internet(1) security(5) mechanisms(5) spkm(1) spkmGssTokens(10)}
--not impl 
--not impl 
-- For CAP Modules
--not impl datatypes                       OBJECT IDENTIFIER ::=
--not impl     {ccitt(0) identified-organization(4) etsi(0) mobileDomain(0) umts-network(1) modules(3)
--not impl     cAP-datatypes(52) version3(2)}
--not impl 
--not impl errortypes                      OBJECT IDENTIFIER ::=
--not impl     {ccitt(0) identified-organization(4) etsi(0) mobileDomain(0) umts-network(1) modules(3)
--not impl     cAP-errortypes(51) version3(2)}
--not impl 
--not impl operationcodes                  OBJECT IDENTIFIER ::= 
--not impl     {ccitt(0) identified-organization(4) etsi(0) mobileDomain(0) umts-network(1) modules(3)
--not impl     cAP-operationcodes(53) version3(2)}
--not impl 
--not impl errorcodes                      OBJECT IDENTIFIER ::=
--not impl     {ccitt(0) identified-organization(4) etsi(0) mobileDomain(0) umts-network(1) modules(3)
--not impl     cAP-errorcodes(57) version3(2)}
--not impl 
--not impl classes                         OBJECT IDENTIFIER ::=
--not impl     {ccitt(0) identified-organization(4) etsi(0) mobileDomain(0) umts-network(1) modules(3)
--not impl     cAP-classes(54) version3(2)}
--not impl 
--not impl gsmSSF-gsmSCF-Operations        OBJECT IDENTIFIER ::=
--not impl     {ccitt(0) identified-organization(4) etsi(0) mobileDomain(0) umts-network(1) modules(3)
--not impl     cAP-gsmSSF-gsmSCF-ops-args(58) version3(2)}
--not impl 
--not impl gsmSSF-gsmSCF-Protocol          OBJECT IDENTIFIER ::=
--not impl     {ccitt(0) identified-organization(4) etsi(0) mobileDomain(0) umts-network(1) modules(3)
--not impl     cAP-gsmSSF-gsmSCF-pkgs-contracts-acs(6) version3(0)}
--not impl 
--not impl gsmSCF-gsmSRF-Operations        OBJECT IDENTIFIER ::=
--not impl     {ccitt(0) identified-organization(4) etsi(0) mobileDomain(0) umts-network(1) modules(3)
--not impl     cAP-gsmSCF-gsmSRF-ops-args (7) version3(0)}
--not impl 
--not impl gsmSCF-gsmSRF-Protocol          OBJECT IDENTIFIER ::=   
--not impl     {ccitt(0) identified-organization(4) etsi(0) mobileDomain(0) umts-network(1) modules(3)
--not impl     cAP-gsmSCF-gsmSRF-pkgs-contracts-acs (8) version3(0)}
--not impl 
--not impl sms-Operations                  OBJECT IDENTIFIER ::= 
--not impl     {ccitt(0) identified-organization(4) etsi(0) mobileDomain(0) umts-network(1) modules(3)
--not impl     cAP-SMS-ops-args (22) version3(0)}
--not impl 
--not impl smsSSF-gsmSCF-Protocol          OBJECT IDENTIFIER ::= 
--not impl     {ccitt(0) identified-organization(4) etsi(0) mobileDomain(0) umts-network(1) modules(3)
--not impl     cAP-smsSSF-gsmSCF-pkgs-contracts-acs (23) version3(0)}
--not impl 
--not impl gprsSSF-gsmSCF-Operations       OBJECT IDENTIFIER ::= 
--not impl     {ccitt(0) identified-organization(4) etsi(0) mobileDomain(0) umts-network(1) modules(3)
--not impl     cAP-GPRS-ops-args (24) version3(1)}
--not impl 
--not impl gprsSSF-gsmSCF-Protocol         OBJECT IDENTIFIER ::= 
--not impl     {ccitt(0) identified-organization(4) etsi(0) mobileDomain(0) umts-network(1) modules(3)
--not impl     cAP-gprsSSF-gsmSCF-pkgs-contracts-acs (25) version3(0)}
--not impl 
--not impl id-CAP                          OBJECT IDENTIFIER ::= 
--not impl     {ccitt(0) identified-organization(4) ccitt(0) identified-organization(4) etsi(0) mobileDomain(0)
--not impl     umts-network(1) cAP3(20)}
--not impl id-CAP0E                        OBJECT IDENTIFIER ::= 
--not impl     {ccitt(0) identified-organization(4) ccitt(0) identified-organization(4) etsi(0) mobileDomain(0)
--not impl     umts-network(1) cAP3OE(21)}
--not impl id-ac                                       OBJECT IDENTIFIER ::= {id-CAP       ac(3)}
--not impl id-acE                                      OBJECT IDENTIFIER ::= {id-CAP0E     ac(3)}
--not impl id-as                                       OBJECT IDENTIFIER ::= {id-CAP       as(5)}
--not impl id-asE                                      OBJECT IDENTIFIER ::= {id-CAP0E     as(5)}
--not impl id-rosObject                                OBJECT IDENTIFIER ::= {id-CAP       rosObject(25)}
--not impl id-contract                                 OBJECT IDENTIFIER ::= {id-CAP       contract(26)}
--not impl id-contractE                                OBJECT IDENTIFIER ::= {id-CAP0E     contract(26)}
--not impl id-package                                  OBJECT IDENTIFIER ::= {id-CAP       package(27)}
--not impl id-packageE                                 OBJECT IDENTIFIER ::= {id-CAP0E     package(27)}
--not impl 
-- for ac, as, rosObject, contract and package, the values are identical to Q.1218
--not impl 
-- ROS Objects
--not impl 
--not impl id-rosObject-gsmSCF                         OBJECT IDENTIFIER ::= {id-rosObject 4}
--not impl id-rosObject-gsmSSF                         OBJECT IDENTIFIER ::= {id-rosObject 5}
--not impl id-rosObject-gsmSRF                         OBJECT IDENTIFIER ::= {id-rosObject 6}
--not impl 
-- gsmSSF/gsmSCF AC
--not impl id-ac-CAP-gsmSSF-scfGenericAC               OBJECT IDENTIFIER ::= {id-acE 4}
--not impl id-ac-CAP-gsmSSF-scfAssistHandoffAC         OBJECT IDENTIFIER ::= {id-acE 6}
--not impl 
-- gsmSRF/gsmSCF AC
--not impl id-ac-gsmSRF-gsmSCF                         OBJECT IDENTIFIER ::= {id-ac 14}
--not impl 
-- gprsSSF/gsmSCF AC
--not impl id-ac-CAP-gprsSSF-gsmSCF-AC                 OBJECT IDENTIFIER ::= {id-acE 50}
--not impl id-ac-CAP-gsmSCF-gprsSSF-AC                 OBJECT IDENTIFIER ::= {id-acE 51}
--not impl 
-- gprsSSF/gsmSCF or gsmSSF/gsmSCF AC
--not impl id-ac-cap3-sms-AC                           OBJECT IDENTIFIER ::= {id-acE 61}
--not impl 
-- gsmSSF/gsmSCF Contracts
--not impl id-CAPSsfToScfGeneric                       OBJECT IDENTIFIER ::= {id-contractE 3}
--not impl id-CAPAssistHandoffssfToScf                 OBJECT IDENTIFIER ::= {id-contractE 5}
--not impl 
-- gsmSRF/gsmSCF Contracts
--not impl id-contract-gsmSRF-gsmSCF                   OBJECT IDENTIFIER ::= {id-contract 13}
--not impl 
-- gprsSSF/gsmSCF Contracts
--not impl id-cap3GprsSsfTogsmScf                      OBJECT IDENTIFIER ::= {id-contract 14}
--not impl id-cap3GgsmSCFTogprsSSF                     OBJECT IDENTIFIER ::= {id-contract 15}
--not impl 
-- gprsSSF/gsmSCF or gsmSSF/gsmSCF Contracts
--not impl id-cap3GprsSsfTogsmScf                      OBJECT IDENTIFIER ::= {id-acE 15}
--not impl 
-- gsmSSF/gsmSCF Operation Packages
--not impl id-package-scfActivation                    OBJECT IDENTIFIER ::= {id-package 11}
--not impl id-package-gsmSRF-scfActivationOfAssist     OBJECT IDENTIFIER ::= {id-package 15} 
--not impl id-package-assistConnectionEstablishment    OBJECT IDENTIFIER ::= {id-package 16} 
--not impl id-package-genericDisconnectResource        OBJECT IDENTIFIER ::= {id-package 17} 
--not impl id-package-nonAssistedConnectionEstablishment
--not impl                                             OBJECT IDENTIFIER ::= {id-package 18} 
--not impl id-package-connect                          OBJECT IDENTIFIER ::= {id-package 19} 
--not impl id-package-callHandling                     OBJECT IDENTIFIER ::= {id-packageE 20} 
--not impl id-package-bcsmEventHandling                OBJECT IDENTIFIER ::= {id-package 21} 
--not impl id-package-ssfCallProcessing                OBJECT IDENTIFIER ::= {id-packageE 24} 
--not impl id-package-timer                            OBJECT IDENTIFIER ::= {id-package 26} 
--not impl id-package-billing                          OBJECT IDENTIFIER ::= {id-package 27} 
--not impl id-package-charging                         OBJECT IDENTIFIER ::= {id-package 28}
--not impl id-package-trafficManagement                OBJECT IDENTIFIER ::= {id-package 29}
--not impl id-package-callReport                       OBJECT IDENTIFIER ::= {id-package 32} 
--not impl id-package-signallingControl                OBJECT IDENTIFIER ::= {id-package 33} 
--not impl id-package-activityTest                     OBJECT IDENTIFIER ::= {id-package 34} 
--not impl id-package-cancel                           OBJECT IDENTIFIER ::= {id-packageE 36} 
--not impl 
-- gsmSRF/gsmSCF Operation Packages
--not impl id-package-specializedResourceControl       OBJECT IDENTIFIER ::= {id-package 42}
--not impl id-package-gsmSRF-scfCancel                 OBJECT IDENTIFIER ::= {id-package 43}
--not impl 
-- gprsSSF/gsmSCF Operation Packages
--not impl id-package-gprsSCFActivationPackage         OBJECT IDENTIFIER ::= {id-package 51}
--not impl id-package-gprsConnectPackage               OBJECT IDENTIFIER ::= {id-package 52}
--not impl id-package-gprsReleasePackage               OBJECT IDENTIFIER ::= {id-package 53}
--not impl id-package-gprsEventHandlingPackage         OBJECT IDENTIFIER ::= {id-package 54}
--not impl id-package-gprsSCFTimerPackage              OBJECT IDENTIFIER ::= {id-package 55}
--not impl id-package-gprsSCFBillingPackage            OBJECT IDENTIFIER ::= {id-package 56}
--not impl id-package-gprsSCFChargingPackage           OBJECT IDENTIFIER ::= {id-package 57}
--not impl id-package-gprsSCFActivityTestPackage       OBJECT IDENTIFIER ::= {id-package 58}
--not impl id-package-gprsSCFCancelPackage             OBJECT IDENTIFIER ::= {id-package 59}
--not impl id-package-gprsSCFChargeAdvicePackage       OBJECT IDENTIFIER ::= {id-package 60}
--not impl id-package-gprsContinue                     OBJECT IDENTIFIER ::= {id-package 49}
--not impl id-package-gprsExceptionInformation         OBJECT IDENTIFIER ::= {id-package 50}
--not impl 
-- gprsSSF/gsmSCF or gsmSSF/gsmSCF Operation Packages
--not impl id-package-smsActivation                    OBJECT IDENTIFIER ::= {id-package 61}
--not impl id-package-smsConnect                       OBJECT IDENTIFIER ::= {id-package 62}
--not impl id-package-smsContinue                      OBJECT IDENTIFIER ::= {id-package 63}
--not impl id-package-smsRelease                       OBJECT IDENTIFIER ::= {id-package 64}
--not impl id-package-smsEventHandling                 OBJECT IDENTIFIER ::= {id-package 65}
--not impl id-package-smsBilling                       OBJECT IDENTIFIER ::= {id-package 66}
--not impl id-package-smsActivityTest                  OBJECT IDENTIFIER ::= {id-package 67}
--not impl id-package-smsTimer                         OBJECT IDENTIFIER ::= {id-package 68} 
--not impl 
-- gsmSSF/gsmSCF Abstract Syntaxes
--not impl id-as-gsmSSF-scfGenericAS                   OBJECT IDENTIFIER ::= {id-asE 4}
--not impl id-as-assistHandoff-gsmSSF-scfAS            OBJECT IDENTIFIER ::= {id-asE 6}
--not impl 
-- gsmSRF/gsmSCF Abstract Syntaxes
--not impl id-as-basic-gsmSRF-gsmSCF                   OBJECT IDENTIFIER ::= {id-as 14}
--not impl 
-- gprsSSF/gsmSCF Abstract Syntaxes
--not impl id-as-gprsSSF-gsmSCF-AS                     OBJECT IDENTIFIER ::= {id-as 50}
--not impl id-as-gsmSCF-gprsSSF-AS                     OBJECT IDENTIFIER ::= {id-as 51}
--not impl 
-- gprsSSF/gsmSCF or gsmSSF/gsmSCF Abstract Syntaxes
--not impl id-as-sms-AS                                OBJECT IDENTIFIER ::= {id-as 61}
--not impl 
--not impl END
--not impl 

--------------------------------------------------------------------------------
--------------------------------------------------------------------------------
--------------------------------------------------------------------------------

-- User Abort Data

CAP-U-ABORT-REASON ::= ENUMERATED {
	no-reason-given				(1),
	application-timer-expired	(2),
	not-allowed-procedures		(3),
	abnormal-processing			(4),
	congestion					(5),
	invalid-reference			(6),
	missing-reference			(7),
	overlapping-dialogue		(8)
	}
-- application-timer-expired	shall be set when application timer (e.g. Tssf) is expired.
-- not-allowed-procedures		shall be set when received signal is not allowed in CAP
--								procedures.
--								For example, when a class 4 operation is received from the
--								gsmSCF and the operation is not allowed in gsmSSF FSM.
--								(gsmSSF FSM cannot continue state transition). (e.g. ReleaseCall
--								operation received in Waiting for End of Temporary Connection
--								state.)
-- abnormal-processing			shall be set when abnormal procedures occur at entity action.
-- congestion					shall be set when requested resource is unavailable due to
--								congestion at TC user (CAP) level.
-- invalid-reference			shall be set if the received destinationReference is unknown or
--								for a known destination Reference the received originationReference
--								does not match with the stored originationReference.
--								This abort reason is used for CAP defined GPRS-ReferenceNumber.
-- missing-reference			shall be set when the destinationReference or the 
--								originationReference is absent in the received message but is
--								required to be present according to the procedures in
--								subclause 14.1.7.
--								This abort reason is used for CAP defined GPRS-ReferenceNumber.
-- overlapping-dialogue			shall be used by the gprsSSF to indicate to the gsmSCF that a 
--								specific instance already has a TC dialogue open. This error
--								cause is typically obtained when both the gsmSCF and gprsSSF
--								open a new dialogue at the same time. 
-- no-reason-given				shall be set when any other reasons above do not apply
-- END of CAP-U-ABORT-Data


-- Module ----------------------------------------------------------------------
--------------------------------------------------------------------------------
-- CAP gsmSSF/CCF - gsmSCF Interface Operations and Arguments.
--------------------------------------------------------------------------------
--------------------------------------------------------------------------------

-- This module contains the operations and operation arguments used for the
-- gsmSSF - gsmSCF interface, for the control of circuit switched calls.

-- The table in subclause 2.1 lists the specifications that contain the modules
-- that are used by CAP.



ApplyChargingArg --{PARAMETERS-BOUND : bound}-- ::= SEQUENCE {
	aChBillingChargingCharacteristics	[0] AChBillingChargingCharacteristics --{bound}--,
	partyToCharge						[2] SendingSideID --DEFAULT sendingSideID : leg1--,
	extensions							[3] SEQUENCE SIZE(1.. -- bound.& -- numOfExtensions) OF 
                                                        ExtensionField   -- {bound} --  OPTIONAL,
	aChChargingAddress					[50] AChChargingAddress --{bound}--
												,
	...
	}

-- The partyToCharge parameter indicates the party in the call to which the ApplyCharging operation
-- shall be applied.


-- Direction: gsmSSF -> gsmSCF, Timer: Tacr 
-- This operation is used by the gsmSSF to report to the gsmSCF the occurrence of a 
-- specific charging event as requested by the gsmSCF using the ApplyCharging operation.

ApplyChargingReportArg --{PARAMETERS-BOUND : bound}-- ::= CallResult --{bound}--


-- Direction: gsmSSF -> gsmSCF or gsmSRF -> gsmSCF, Timer: Tari
-- This operation is used when there is an assist procedure and may be
-- sent by the gsmSSF or gsmSRF to the gsmSCF. This operation is sent by the
-- assisting gsmSSF to gsmSCF, when the initiating gsmSSF has set up a connection to
-- the gsmSRF or to the assisting gsmSSF as a result of receiving an 
-- EstablishTemporaryConnection from
-- the gsmSCF.
-- Refer to clause 11 for a description of the procedures associated with this operation.

AssistRequestInstructionsArg --{PARAMETERS-BOUND : bound}-- ::= SEQUENCE {
	correlationID						[0] CorrelationID --{bound}--,
	iPSSPCapabilities					[2] IPSSPCapabilities --{bound}--,
	extensions							[3] SEQUENCE SIZE(1.. -- bound.& -- numOfExtensions) OF 
                                                        ExtensionField   -- {bound} --  OPTIONAL,
	...
	}
-- OPTIONAL denotes network operator specific use. The value of the correlationID may be the 
-- Called Party Number supplied by the initiating gsmSSF.


-- Direction: gsmSCF -> gsmSSF, Timer: Tcg 
-- This operation is used to request the gsmSSF to reduce the rate at which specific service 
-- requests are sent to the gsmSCF.

CallGapArg --{PARAMETERS-BOUND : bound}--::= SEQUENCE {
	gapCriteria							[0] GapCriteria --{bound}--,
	gapIndicators						[1] GapIndicators,
	controlType							[2] ControlType								OPTIONAL,
	gapTreatment						[3] GapTreatment --{bound}--					OPTIONAL,
	extensions							[4] SEQUENCE SIZE(1.. -- bound.& -- numOfExtensions) OF 
                                                        ExtensionField   -- {bound} --  OPTIONAL,
	...
	}
-- OPTIONAL denotes network operator optional. If gapTreatment is not present, then the gsmSSF will 
-- use a default treatment depending on network operator implementation.


-- Direction: gsmSSF -> gsmSCF, Timer: Tcirp 
-- This operation is used to send specific call information for a single call party to the gsmSCF as 
-- requested by the gsmSCF in a previous CallInformationRequest.

CallInformationReportArg --{PARAMETERS-BOUND : bound}-- ::= SEQUENCE {
	requestedInformationList			[0] RequestedInformationList --{bound}--,
	extensions							[2] SEQUENCE SIZE(1.. -- bound.& -- numOfExtensions) OF 
                                                        ExtensionField   -- {bound} --  OPTIONAL,
	legID								[3] ReceivingSideID							OPTIONAL,
	...
	}


-- Direction: gsmSCF -> gsmSSF, Timer: Tcirq 
-- This operation is used to request the gsmSSF to record specific information about a single
-- call party and report it to the gsmSCF (with a CallInformationReport operation). 

CallInformationRequestArg --{PARAMETERS-BOUND : bound}--::= SEQUENCE {
	requestedInformationTypeList		[0] RequestedInformationTypeList --{bound}--,
	extensions							[2] SEQUENCE SIZE(1.. -- bound.& -- numOfExtensions) OF 
                                                        ExtensionField   -- {bound} --  OPTIONAL,
	legID								[3] SendingSideID							OPTIONAL,
	...
	}
-- OPTIONAL denotes network operator optional.


-- Direction: gsmSCF -> gsmSSF, or gsmSCF -> gsmSRF, Timer: Tcan 
-- This operation cancels the correlated previous operation or all previous requests. The following 
-- operations can be canceled: PlayAnnouncement, PromptAndCollectUserInformation.

CancelArg ::= CHOICE {
	invokeID							[0] InvokeID,
	allRequests							[1] NULL,
	callSegmentToCancel					[2]	CallSegmentToCancel
	}
-- The InvokeID has the same value as that which was used for the operation to be cancelled.


-- Direction: gsmSCF-> gsmSSF, Timer: Tcon 
-- This operation is used to request the gsmSSF to perform the call processing actions
-- to route or forward a call to a specified destination.

ConnectArg --{PARAMETERS-BOUND : bound}-- ::= SEQUENCE {
	destinationRoutingAddress			[0] DestinationRoutingAddress --{bound}--,
	alertingPattern						[1] AlertingPattern							OPTIONAL,
	originalCalledPartyID				[6] OriginalCalledPartyID --{bound}--			OPTIONAL,
	extensions							[10] SEQUENCE SIZE(1.. -- bound.& -- numOfExtensions) OF 
                                                        ExtensionField   -- {bound} --  OPTIONAL,
	carrier								[11] Carrier --{bound}--						OPTIONAL,
	callingPartysCategory				[28] CallingPartysCategory					OPTIONAL,
	redirectingPartyID					[29] RedirectingPartyID --{bound}--				OPTIONAL,
	redirectionInformation				[30] RedirectionInformation					OPTIONAL,
	genericNumbers						[14] GenericNumbers --{bound}--					OPTIONAL,
	serviceInteractionIndicatorsTwo 	[15] ServiceInteractionIndicatorsTwo		OPTIONAL,
	chargeNumber						[19] ChargeNumber --{bound}--					OPTIONAL,
	legToBeCreated						[21] LegID									OPTIONAL,
	cug-Interlock						[31] CUG-Interlock							OPTIONAL,
	cug-OutgoingAccess					[32] NULL									OPTIONAL,
	suppressionOfAnnouncement			[55] SuppressionOfAnnouncement				OPTIONAL,
	oCSIApplicable						[56] OCSIApplicable							OPTIONAL,
	naOliInfo							[57] NAOliInfo								OPTIONAL,
	bor-InterrogationRequested			[58] NULL									OPTIONAL,
	...
	}
-- na-Info is included at the discretion of the gsmSCF operator.


-- Direction: gsmSCF -> gsmSSF, Timer: Tctr 
-- This operation is used to connect a call segment from the gsmSSF to the
-- gsmSRF.

ConnectToResourceArg --{PARAMETERS-BOUND : bound}-- ::= SEQUENCE {
	resourceAddress	CHOICE {
		ipRoutingAddress					[0] IPRoutingAddress --{bound}--,
		none								[3] NULL
		},
	extensions							[4] SEQUENCE SIZE(1.. -- bound.& -- numOfExtensions) OF 
                                                        ExtensionField   -- {bound} --  OPTIONAL,
	serviceInteractionIndicatorsTwo		[7] ServiceInteractionIndicatorsTwo			OPTIONAL,
	callSegmentID						[50] CallSegmentID --{bound}--					OPTIONAL,
	...
	}


-- Direction: gsmSCF -> gsmSSF, Timer: Tcue 
-- This operation is used to request the gsmSSF to proceed with call processing at the
-- DP at which it previously suspended call processing to await gsmSCF instructions
-- (i.e. proceed to the next point in call in the BCSM). The gsmSSF continues call
-- processing without substituting new data from gsmSCF.


-- Direction: gsmSCF -> gsmSSF, Timer: Tcwa 
-- This operation is used to request the gsmSSF to proceed with call processing at the
-- DP at which it previously suspended call processing to await gsmSCF instructions
-- (i.e. proceed to the next point in call in the BCSM). The gsmSSF continues call
-- processing with the modified call setup information as received from the gsmSCF.

ContinueWithArgumentArg --{PARAMETERS-BOUND : bound}-- ::= SEQUENCE {
	legID								[0]	LegID									OPTIONAL,
	alertingPattern						[1] AlertingPattern							OPTIONAL,
	extensions							[6] SEQUENCE SIZE(1.. -- bound.& -- numOfExtensions) OF 
                                                        ExtensionField   -- {bound} --  OPTIONAL,
	serviceInteractionIndicatorsTwo		[7] ServiceInteractionIndicatorsTwo			OPTIONAL,
	callingPartysCategory				[12] CallingPartysCategory					OPTIONAL,
	genericNumbers						[16] GenericNumbers --{bound}--					OPTIONAL,
	cug-Interlock						[17] CUG-Interlock							OPTIONAL,
	cug-OutgoingAccess					[18] NULL									OPTIONAL,
	chargeNumber						[50] ChargeNumber --{bound}--					OPTIONAL,
	carrier								[52] Carrier --{bound}--						OPTIONAL,
	suppressionOfAnnouncement			[55] SuppressionOfAnnouncement				OPTIONAL,
	naOliInfo							[56] NAOliInfo								OPTIONAL,
	bor-InterrogationRequested			[57] NULL									OPTIONAL,
	suppress-O-CSI						[58] NULL									OPTIONAL,
	continueWithArgumentArgExtension 	[59] ContinueWithArgumentArgExtension		OPTIONAL,
	...
	}

ContinueWithArgumentArgExtension ::= SEQUENCE {
	suppress-D-CSI						[0]	NULL									OPTIONAL,
	suppress-N-CSI						[1]	NULL									OPTIONAL,
	suppressOutgoingCallBarring			[2]	NULL									OPTIONAL,
	...
	}


-- Direction: gsmSCF -> gsmSSF, Timer: Tdfc
-- This operation is used to disconnect a forward temporary connection or a connection to a 
-- resource. Refer to clause 11 for a description of the procedures associated with this operation. 


-- Direction gsmSCF -> gsmSSF, Timer Tdfcwa
-- This operation is used to disconnect a forward temporary connection or a connection to a
-- resource. Refer to clause 11 for a description of the procedures associated with this operation.

DisconnectForwardConnectionWithArgumentArg --{PARAMETERS-BOUND : bound}-- ::= SEQUENCE {
	callSegmentID						[1]	CallSegmentID --{bound}--					OPTIONAL,
	extensions							[2] SEQUENCE SIZE(1.. -- bound.& -- numOfExtensions) OF 
                                                        ExtensionField   -- {bound} --  OPTIONAL,
	...
	}

-- Direction: gsmSCF -> gsmSSF, Timer Tdl
-- This operation is used by the gsmSCF to release a specific leg associated with the call and
-- retain any other legs not specified in the DisconnectLeg. Refer to clause 11 for a description
-- of the procedures associated with this operation.

DisconnectLegArg --{PARAMETERS-BOUND : bound}-- ::= SEQUENCE {
	legToBeReleased						[0]	LegID,
	releaseCause						[1]	Cause --{bound}--							OPTIONAL,
	extensions							[2]	SEQUENCE SIZE(1.. -- bound.& -- numOfExtensions) OF 
                                                        ExtensionField   -- {bound} --  OPTIONAL,
	...
	}


-- Direction: gsmSSF -> gsmSCF, Timer: Ter
-- This operation is used by the gsmSSF to inform the gsmSCF of an error or exception

EntityReleasedArg --{PARAMETERS-BOUND : bound}-- ::= CHOICE {
	callSegmentFailure					[0]	CallSegmentFailure,
	bCSM-Failure						[1]	BCSM-Failure
	}


-- Direction: gsmSCF -> gsmSSF, Timer: Tetc 
-- This operation is used to create a connection to a resource for a limited period
-- of time (e.g. to play an announcement, to collect user information); it implies
-- the use of the assist procedure. Refer to clause 11 for a description of the
-- procedures associated with this operation.

EstablishTemporaryConnectionArg --{PARAMETERS-BOUND : bound}-- ::= SEQUENCE {
	assistingSSPIPRoutingAddress		[0] AssistingSSPIPRoutingAddress --{bound}--,
	correlationID						[1] CorrelationID --{bound}--					OPTIONAL,
	scfID								[3] ScfID --{bound}--							OPTIONAL,
	extensions							[4] SEQUENCE SIZE(1.. -- bound.& -- numOfExtensions) OF 
                                                        ExtensionField   -- {bound} --  OPTIONAL,
	carrier								[5] Carrier --{bound}--							OPTIONAL,
	serviceInteractionIndicatorsTwo		[6] ServiceInteractionIndicatorsTwo			OPTIONAL,
	callSegmentID						[7]	CallSegmentID --{bound}--					OPTIONAL,
	naOliInfo							[50] NAOliInfo								OPTIONAL,
	chargeNumber						[51] ChargeNumber --{bound}--					OPTIONAL,
	...
	}


-- Direction: gsmSSF -> gsmSCF, Timer: Tenc
-- This operation is used by the gsmSSF to report to the gsmSCF the occurrence of a
-- specific charging event type as previously requested by the gsmSCF in a
-- RequestNotificationChargingEvent operation.

EventNotificationChargingArg --{PARAMETERS-BOUND : bound}-- ::= SEQUENCE { 
	eventSpecificChargingInformation	[1] EventSpecificChargingInformation--{ bound}--, 
	legID								[2] LegID									OPTIONAL,
	extensions							[3] SEQUENCE SIZE(1.. -- bound.& -- numOfExtensions) OF 
                                                        ExtensionField   -- {bound} --  OPTIONAL,
	...
	}


-- Direction: gsmSSF -> gsmSCF, Timer: Terb
-- This operation is used to notify the gsmSCF of a call-related event (e.g. BCSM
-- events such as O_Busy or O_No_Answer) previously requested by the gsmSCF in a
-- RequestReportBCSMEvent operation.

EventReportBCSMArg --{PARAMETERS-BOUND : bound}-- ::= SEQUENCE {
	eventTypeBCSM						[0] EventTypeBCSM,
	eventSpecificInformationBCSM		[2] EventSpecificInformationBCSM --{bound}--	OPTIONAL,
	legID								[3] ReceivingSideID							OPTIONAL,
	miscCallInfo						[4] MiscCallInfo --DEFAULT {messageType request}--,
	extensions							[5] SEQUENCE SIZE(1.. -- bound.& -- numOfExtensions) OF 
                                                        ExtensionField   -- {bound} --  OPTIONAL,
	...
	}


-- Direction: gsmSCF -> gsmSSF, Timer: Tfci
-- This operation is used to request the gsmSSF to generate, register a call record
-- or to include some information in the default call record.
-- The registered call record is intended for off line charging of the call.

FurnishChargingInformationArg --{PARAMETERS-BOUND : bound}-- ::=
	FCIBillingChargingCharacteristics--{bound}--


-- Direction: gsmSSF -> gsmSCF, Timer: Tidp 
-- This operation is used after a TDP to indicate request for service.

InitialDPArg --{PARAMETERS-BOUND : bound}-- ::= SEQUENCE {
	serviceKey							[0] ServiceKey	,
	calledPartyNumber					[2] CalledPartyNumber --{bound}--				OPTIONAL,
	callingPartyNumber					[3] CallingPartyNumber --{bound}--				OPTIONAL,
	callingPartysCategory				[5] CallingPartysCategory					OPTIONAL,
	cGEncountered						[7] CGEncountered							OPTIONAL,
	iPSSPCapabilities					[8] IPSSPCapabilities --{bound}--				OPTIONAL,
	locationNumber						[10] LocationNumber --{bound}--					OPTIONAL,
	originalCalledPartyID				[12] OriginalCalledPartyID --{bound}--			OPTIONAL,
	extensions							[15] SEQUENCE SIZE(1.. -- bound.& -- numOfExtensions) OF 
                                                        ExtensionField   -- {bound} --  OPTIONAL,
	highLayerCompatibility				[23] HighLayerCompatibility					OPTIONAL,
	additionalCallingPartyNumber		[25] AdditionalCallingPartyNumber --{bound}--	OPTIONAL,
	bearerCapability					[27] BearerCapability --{bound}--				OPTIONAL,
	eventTypeBCSM						[28] EventTypeBCSM							OPTIONAL,
	redirectingPartyID					[29] RedirectingPartyID --{bound}--				OPTIONAL,
	redirectionInformation				[30] RedirectionInformation					OPTIONAL,
	cause								[17] Cause --{bound}--							OPTIONAL,
	serviceInteractionIndicatorsTwo		[32] ServiceInteractionIndicatorsTwo		OPTIONAL,
	carrier								[37] Carrier --{bound}--						OPTIONAL,
	cug-Index							[45] CUG-Index								OPTIONAL,
	cug-Interlock						[46] CUG-Interlock							OPTIONAL,
	cug-OutgoingAccess					[47] NULL									OPTIONAL,
	iMSI								[50] IMSI									OPTIONAL,
	subscriberState						[51] SubscriberState						OPTIONAL,
	locationInformation					[52] LocationInformation					OPTIONAL,
	ext-basicServiceCode				[53] Ext-BasicServiceCode					OPTIONAL,
	callReferenceNumber					[54] CallReferenceNumber					OPTIONAL,
	mscAddress							[55] ISDN-AddressString						OPTIONAL,
	calledPartyBCDNumber				[56] CalledPartyBCDNumber --{bound}--			OPTIONAL,
	timeAndTimezone						[57] TimeAndTimezone --{bound}--				OPTIONAL,
	callForwardingSS-Pending			[58] NULL									OPTIONAL,
	initialDPArgExtension				[59] InitialDPArgExtension					OPTIONAL,
	...
	}

-- Imported from MAP

TBCD-STRING ::= OCTET STRING
    -- This type (Telephony Binary Coded Decimal String) is used to
    -- represent several digits from 0 through 9, *, #, a, b, c, two
    -- digits per octet, each digit encoded 0000 to 1001 (0 to 9),
    -- 1010 (*), 1011 (#), 1100 (a), 1101 (b) or 1110 (c); 1111 used
    -- as filler when there is an odd number of digits.

    -- bits 8765 of octet n encoding digit 2n
    -- bits 4321 of octet n encoding digit 2(n-1) +1

IMEI ::= TBCD-STRING (SIZE (8))
    --  Refers to International Mobile Station Equipment Identity
    --  and Software Version Number (SVN) defined in TS GSM 03.03.
    --  If the SVN is not present the last octet shall contain the
    --  digit 0 and a filler.
    --  If present the SVN shall be included in the last octet.

SupportedCamelPhases ::= BIT STRING {
    phase1 (0),
    phase2 (1) ,
    phase3 (2) } (SIZE (1..16)) 
-- A node shall mark in the BIT STRING all CAMEL Phases it supports.
-- Other values than listed above shall be discarded.

------------------------------------------------------
--
-- Imported from GSMMAP V8
--
------------------------------------------------------

MS-Classmark2 ::= OCTET STRING (SIZE (3))
-- This parameter carries the value part of the MS Classmark 2 IE defined in
-- 3GPP TS 24.008 [35].


SupportedCamel4Subsets ::= BIT STRING {
cs-CallHandling (0),
chargingNotification (1),
cAMELControlOver-MT-SMS (2),
gprs-MobilityManagement (3),
gprs-AnyTimeInterrogation (4)
} (SIZE (5..16))
-- A node supporting Camel phase 4 shall mark in the BIT STRING all Camel4 subsets
-- it supports.
-- Other values than listed above shall be discarded.

------------------------------------------------------
--
-- End of Imported from GSMMAP V8
--
------------------------------------------------------

InitialDPArgExtension ::= SEQUENCE {
	gmscAddress							[0] ISDN-AddressString						OPTIONAL,
	forwardingDestinationNumber			[1] CalledPartyNumber --{bound}--				OPTIONAL,
	ms-Classmark2						[2] MS-Classmark2							OPTIONAL,
	iMEI								[3] IMEI									OPTIONAL,
	supportedCamelPhases				[4] SupportedCamelPhases					OPTIONAL,
	supportedCamel4Subsets				[5] SupportedCamel4Subsets					OPTIONAL,
	...
}
-- If iPSSPCapabilities is not present then this denotes that a colocated gsmSRF is not 
-- supported by the gsmSSF. If present, then the gsmSSF supports a colocated gsmSRF capable 
-- of playing announcements via elementaryMessageIDs and variableMessages, the playing of
-- tones and the collection of DTMF digits. Other supported capabilities are explicitly 
-- detailed in the IPSSPCapabilities parameter itself.
-- Carrier is included at the discretion of the gsmSSF operator.


-- Direction: gsmSCF -> gsmSSF, Timer Tica
-- This operation is used to instruct the gsmSSF to create a new call to a call party using the
-- address information provided by the gsmSCF.

InitiateCallAttemptArg --{PARAMETERS-BOUND : bound}-- ::= SEQUENCE {
	destinationRoutingAddress			[0]	DestinationRoutingAddress --{bound}--,
	extensions							[4]	SEQUENCE SIZE(1.. -- bound.& -- numOfExtensions) OF 
                                                        ExtensionField   -- {bound} --  OPTIONAL,
	legToBeCreated						[5]	LegID									OPTIONAL,
	newCallSegment						[6]	CallSegmentID --{bound}--					OPTIONAL,
	callingPartyNumber					[30] CallingPartyNumber --{bound}--				OPTIONAL,
	callReferenceNumber					[51] CallReferenceNumber					OPTIONAL,
	gsmSCFAddress						[52] ISDN-AddressString						OPTIONAL,
	suppress-T-CSI						[53] NULL									OPTIONAL,
	...
	}

InitiateCallAttemptRes --{PARAMETERS-BOUND : bound}-- ::= SEQUENCE {
	supportedCamelPhases				[0] SupportedCamelPhases					OPTIONAL,
	supportedCamel4Subsets				[1] SupportedCamel4Subsets					OPTIONAL,
	extensions							[2]	SEQUENCE SIZE(1.. -- bound.& -- numOfExtensions) OF 
                                                        ExtensionField   -- {bound} --  OPTIONAL,
	...
	}


-- Direction: gsmSCF -> gsmSSF, Timer: Tml
-- This operation is used by the gsmSCF to move a leg from one call segment to another call seqment
-- within the same call segment association.

MoveLegArg --{PARAMETERS-BOUND : bound}-- ::= SEQUENCE{
	legIDToMove							[0]	LegID,
	extensions							[2]	SEQUENCE SIZE(1.. -- bound.& -- numOfExtensions) OF 
                                                        ExtensionField   -- {bound} --  OPTIONAL,
	...
	}


-- Direction: gsmSCF -> gsmSSF, Timer: Tpt
-- This operation is used to play tones to either a leg or a call segment using
-- the MSC's tone generator.

PlayToneArg --{PARAMETERS-BOUND : bound}-- ::= SEQUENCE {
	legOrCallSegment					[0] LegOrCallSegment --{bound}--,
	bursts								[1] Burst,
	extensions							[2] SEQUENCE SIZE(1.. -- bound.& -- numOfExtensions) OF 
                                                        ExtensionField   -- {bound} --  OPTIONAL,
	...
	}

-- Direction: gsmSCF ->?gsmSSF, Timer: Trc 
-- This operation is used to tear down an existing call at any phase of the call for all parties 
-- involved in the call. 

ReleaseCallArg --{PARAMETERS-BOUND : bound}-- ::= Cause --{bound}-- 
-- A default value of decimal 31 (normal unspecified) shall be given.


-- Direction: gsmSCF -> gsmSSF, Timer: Trnc
-- This operation is used by the gsmSCF to instruct the gsmSSF on how to manage the charging events
-- which are received from other FEs and not under control of the service logic instance.

RequestNotificationChargingEventArg --{PARAMETERS-BOUND : bound}-- ::= SEQUENCE {
	eventTypeChargingPLMN				[0] EventTypeChargingPLMN --{bound}--,
	monitorMode							[1] MonitorMode,
	legID								[2] LegID									OPTIONAL,
	extensions							[3] SEQUENCE SIZE(1.. -- bound.& -- numOfExtensions) OF 
                                                        ExtensionField   -- {bound} --  OPTIONAL,
	...
	}
-- This argument indicates the charging event type and the corresponding monitor mode and LegID.


-- Direction: gsmSCF -> gsmSSF, Timer: Trrb
-- This operation is used to request the gsmSSF to monitor for a call-related event
-- (e.g. BCSM events such as O_Busy or O_No_Answer) and to send a notification
-- to the gsmSCF when the event is detected.
--
-- NOTE:
-- Every EDP must be explicitly armed by the gsmSCF via a RequestReportBCSMEvent operation. 
-- No implicit arming of EDPs at the gsmSSF after reception of any operation (different 
-- from RequestReportBCSMEvent) from the gsmSCF is allowed.

RequestReportBCSMEventArg --{PARAMETERS-BOUND : bound}-- ::= SEQUENCE {
	bcsmEvents							[0] SEQUENCE SIZE(1..--bound.&--numOfBCSMEvents) OF
												BCSMEvent --{bound}--,
	extensions							[2] SEQUENCE SIZE(1.. -- bound.& -- numOfExtensions) OF 
                                                        ExtensionField   -- {bound} --  OPTIONAL,
	...
	}
-- Indicates the BCSM related events for notification.


-- Direction: gsmSCF -> gsmSSF, Timer: Trt 
-- This operation is used to request the gsmSSF to refresh an application timer in the gsmSSF.

ResetTimerArg --{PARAMETERS-BOUND : bound}-- ::= SEQUENCE {
	timerID								[0] TimerID	DEFAULT tssf,
	timervalue							[1] TimerValue,
	extensions							[2] SEQUENCE SIZE(1.. -- bound.& -- numOfExtensions) OF 
                                                        ExtensionField   -- {bound} --  OPTIONAL,
	callSegmentID						[3]	CallSegmentID --{bound}--					OPTIONAL,
	...
	}


-- Direction: gsmSCF -> gsmSSF, Timer: Tsci 
-- This operation is used to instruct the gsmSSF on the charging information to send by the gsmSSF.
-- The charging information can either be sent back by means of signalling or internal
-- if the gsmSSF is located in the local exchange. In the local exchange
-- this information may be used to update the charge meter or to create a standard call record.

SendChargingInformationArg --{PARAMETERS-BOUND : bound}--::= SEQUENCE {
	sCIBillingChargingCharacteristics	[0] SCIBillingChargingCharacteristics --{bound}--,
	partyToCharge						[1] SendingSideID,
	extensions							[2] SEQUENCE SIZE(1.. -- bound.& -- numOfExtensions) OF 
                                                        ExtensionField   -- {bound} --  OPTIONAL,
	...
	}


-- Direction: gsmSCF -> gsmSSF, Timer Tsl
-- This operation is used by the gsmSCF to separate one joined leg from a multi-way connection or
-- a single two party Call Segment.

SplitLegArg --{PARAMETERS-BOUND : bound}-- ::= SEQUENCE {
	legToBeSplit						[0]	LegID,
	newCallSegment						[1]	CallSegmentID --{bound}--					OPTIONAL,
	extensions							[2]	SEQUENCE SIZE(1.. -- bound.& -- numOfExtensions) OF 
                                                        ExtensionField   -- {bound} --  OPTIONAL,
	...
	}
GPRS-ReferenceNumber ::= SEQUENCE {
destinationReference [0] Integer4 OPTIONAL,
originationReference [1] Integer4 OPTIONAL
}
-- This parameter is used to identify the relationship between SGSN and


-- Module ----------------------------------------------------------------------
--------------------------------------------------------------------------------
-- CAP gsmSSF/gsmSCF Packages, Contracts and ACs.
--------------------------------------------------------------------------------
--------------------------------------------------------------------------------
--not impl 
--not impl CAP-gsmSSF-gsmSCF-pkgs-contracts-acs {ccitt(0) identified-organization(4) etsi(0) mobileDomain(0) umts-network(1) modules(3) cAP-gsmSSF-gsmSCF-pkgs-contracts-acs (6) version3(2)}
--not impl 
--not impl DEFINITIONS ::= BEGIN
--not impl 
-- This module describes the operation-packages, contracts and application-contexts used
-- over the gsmSSF-gsmSCF interface.
--not impl 
--not impl IMPORTS
--not impl 
--not impl     PARAMETERS-BOUND,
--not impl     cAPSpecificBoundSet
--not impl FROM CAP-classes classes
--not impl 
--not impl     ROS-OBJECT-CLASS,
--not impl     CONTRACT,
--not impl     OPERATION-PACKAGE,
--not impl     OPERATION
--not impl FROM Remote-Operations-Information-Objects ros-InformationObjects
--not impl 
--not impl     TCMessage {} 
--not impl FROM TCAPMessages tc-Messages
--not impl 
--not impl     APPLICATION-CONTEXT,
--not impl     dialogue-abstract-syntax
--not impl FROM TC-Notation-Extensions tc-NotationExtensions
--not impl 
--not impl     activityTest,
--not impl     applyCharging {},
--not impl     applyChargingReport {},
--not impl     assistRequestInstructions {},
--not impl     callGap {},
--not impl     callInformationReport {},
--not impl     callInformationRequest {},
--not impl     cancel {},
--not impl     connect {},
--not impl     connectToResource {},
--not impl     continue,
--not impl     continueWithArgument {},
--not impl     disconnectForwardConnection,
--not impl     establishTemporaryConnection {},
--not impl     eventReportBCSM {},
--not impl     furnishChargingInformation {},
--not impl     initialDP {},
--not impl     releaseCall {},
--not impl     requestReportBCSMEvent {},
--not impl     resetTimer {},
--not impl     sendChargingInformation {}
--not impl FROM CAP-gsmSSF-gsmSCF-ops-args gsmSSF-gsmSCF-Operations
--not impl 
--not impl     playAnnouncement {},
--not impl     promptAndCollectUserInformation {},
--not impl     specializedResourceReport
--not impl FROM CAP-gsmSCF-gsmSRF-ops-args gsmSCF-gsmSRF-Operations
--not impl 
--not impl     specializedResourceControlPackage {}
--not impl FROM CAP-gsmSCF-gsmSRF-pkgs-contracts-acs gsmSCF-gsmSRF-Protocol
--not impl 
--not impl     id-ac-CAP-gsmSSF-scfGenericAC,
--not impl     id-ac-CAP-gsmSSF-scfAssistHandoffAC,
--not impl     id-CAPSsfToScfGeneric,
--not impl     id-CAPAssistHandoffssfToScf,
--not impl     id-as-gsmSSF-scfGenericAS,
--not impl     id-as-assistHandoff-gsmSSF-scfAS,
--not impl     id-package-scfActivation,
--not impl     id-package-gsmSRF-scfActivationOfAssist,
--not impl     id-package-assistConnectionEstablishment,
--not impl     id-package-genericDisconnectResource,
--not impl     id-package-nonAssistedConnectionEstablishment,
--not impl     id-package-connect,
--not impl     id-package-callHandling,
--not impl     id-package-bcsmEventHandling,
--not impl     id-package-ssfCallProcessing,
--not impl     id-package-timer,
--not impl     id-package-billing,
--not impl     id-package-charging,
--not impl     id-package-trafficManagement,
--not impl     id-package-callReport,
--not impl     id-package-signallingControl,
--not impl     id-package-activityTest,
--not impl     id-package-cancel,
--not impl     classes,
--not impl     ros-InformationObjects,
--not impl     tc-Messages,
--not impl     tc-NotationExtensions, 
--not impl     gsmSSF-gsmSCF-Operations,
--not impl     gsmSCF-gsmSRF-Operations,
--not impl     gsmSCF-gsmSRF-Protocol
--not impl FROM CAP-object-identifiers {ccitt(0) identified-organization(4) etsi(0) mobileDomain(0) umts-network(1) modules(3) cAP-object-identifiers (17) version3(2)}
--not impl 
--not impl ;
--not impl 
-- Application Contexts
--not impl 
--not impl capssf-scfGenericAC APPLICATION-CONTEXT ::= {
--not impl     CONTRACT                    capSsfToScfGeneric
--not impl     DIALOGUE MODE               structured
--not impl     ABSTRACT SYNTAXES           {dialogue-abstract-syntax |
--not impl                                 gsmSSF-scfGenericAbstractSyntax} 
--not impl     APPLICATION CONTEXT NAME    id-ac-CAP-gsmSSF-scfGenericAC}
--not impl 
--not impl capssf-scfAssistHandoffAC APPLICATION-CONTEXT ::=   {
--not impl     CONTRACT                    capAssistHandoffssfToScf
--not impl     DIALOGUE MODE               structured
--not impl     ABSTRACT SYNTAXES           {dialogue-abstract-syntax |
--not impl                                 assistHandoff-gsmSSF-scfAbstractSyntax}
--not impl     APPLICATION CONTEXT NAME    id-ac-CAP-gsmSSF-scfAssistHandoffAC}
--not impl 
--not impl 
-- Contracts
--not impl 
--not impl capSsfToScfGeneric CONTRACT ::= {
-- dialogue initiated by gsmSSF with InitialDP Operation
--not impl     INITIATOR CONSUMER OF   
--not impl             {           scfActivationPackage {cAPSpecificBoundSet}}
--not impl     RESPONDER CONSUMER OF
--not impl             {activityTestPackage|
--not impl             assistConnectionEstablishmentPackage {cAPSpecificBoundSet} |
--not impl             bcsmEventHandlingPackage {cAPSpecificBoundSet} |
--not impl             billingPackage {cAPSpecificBoundSet} |
--not impl             callHandlingPackage {cAPSpecificBoundSet} |
--not impl             callReportPackage {cAPSpecificBoundSet} |
--not impl             cancelPackage {cAPSpecificBoundSet} |
--not impl             chargingPackage {cAPSpecificBoundSet} |
--not impl             connectPackage {cAPSpecificBoundSet} |
--not impl             genericDisconnectResourcePackage {cAPSpecificBoundSet} |
--not impl             nonAssistedConnectionEstablishmentPackage {cAPSpecificBoundSet} |
--not impl             signallingControlPackage {cAPSpecificBoundSet} |
--not impl             specializedResourceControlPackage {cAPSpecificBoundSet} |
--not impl             ssfCallProcessingPackage {cAPSpecificBoundSet} |
--not impl             timerPackage {cAPSpecificBoundSet} |
--not impl             trafficManagementPackage {networkSpecificBoundSet}
--not impl             }
--not impl     ID      id-CAPSsfToScfGeneric
--not impl     }
--not impl 
--not impl capAssistHandoffssfToScf CONTRACT ::= {
-- dialogue initiated by gsmSSF with AssistRequestInstructions
--not impl     INITIATOR CONSUMER OF
--not impl             {gsmSRF-scfActivationOfAssistPackage {cAPSpecificBoundSet}}
--not impl     RESPONDER CONSUMER OF
--not impl             {activityTestPackage|
--not impl             callHandlingPackage {cAPSpecificBoundSet} |
--not impl             cancelPackage {cAPSpecificBoundSet} |
--not impl             genericDisconnectResourcePackage {cAPSpecificBoundSet} |
--not impl             nonAssistedConnectionEstablishmentPackage {cAPSpecificBoundSet} |
--not impl             specializedResourceControlPackage {cAPSpecificBoundSet} |
--not impl             timerPackage {cAPSpecificBoundSet}
--not impl             }
--not impl     ID      id-CAPAssistHandoffssfToScf
--not impl     }
--not impl 
--not impl 
-- Operation Packages
--not impl 
--not impl scfActivationPackage {PARAMETERS-BOUND : bound}  OPERATION-PACKAGE ::= {
--not impl     CONSUMER INVOKES    {initialDP {bound}}
--not impl     ID      id-package-scfActivation}
--not impl gsmSRF-scfActivationOfAssistPackage {PARAMETERS-BOUND : bound} OPERATION-PACKAGE ::= {
--not impl     CONSUMER INVOKES    {assistRequestInstructions {bound}}
--not impl     ID      id-package-gsmSRF-scfActivationOfAssist}
--not impl assistConnectionEstablishmentPackage {PARAMETERS-BOUND : bound}   OPERATION-PACKAGE ::= {
--not impl     CONSUMER INVOKES    {establishTemporaryConnection {bound}}
--not impl     ID      id-package-assistConnectionEstablishment}
--not impl genericDisconnectResourcePackage {PARAMETERS-BOUND : bound}   OPERATION-PACKAGE ::= {
--not impl     CONSUMER INVOKES    {disconnectForwardConnection}
--not impl     ID      id-package-genericDisconnectResource}
--not impl nonAssistedConnectionEstablishmentPackage {PARAMETERS-BOUND : bound} OPERATION-PACKAGE ::= {
--not impl     CONSUMER INVOKES    {connectToResource {bound}}
--not impl     ID      id-package-nonAssistedConnectionEstablishment}
--not impl connectPackage {PARAMETERS-BOUND : bound} OPERATION-PACKAGE ::= {
--not impl     CONSUMER INVOKES    {connect {bound}}
--not impl     ID      id-package-connect}
--not impl callHandlingPackage  {PARAMETERS-BOUND : bound} OPERATION-PACKAGE ::= {
--not impl     CONSUMER INVOKES    {releaseCall {bound}}
--not impl     ID      id-package-callHandling}
--not impl bcsmEventHandlingPackage {PARAMETERS-BOUND : bound} OPERATION-PACKAGE ::= {
--not impl     CONSUMER INVOKES    {requestReportBCSMEvent {bound}}
--not impl     SUPPLIER INVOKES    {eventReportBCSM {bound}}
--not impl     ID      id-package-bcsmEventHandling}
--not impl ssfCallProcessingPackage {PARAMETERS-BOUND : bound} OPERATION-PACKAGE ::= {
--not impl     CONSUMER INVOKES    {continueWithArgument {bound} | continue}
--not impl     ID      id-package-ssfCallProcessing}
--not impl timerPackage {PARAMETERS-BOUND : bound} OPERATION-PACKAGE ::= {
--not impl     CONSUMER INVOKES    {resetTimer {bound}}
--not impl     ID      id-package-timer}
--not impl billingPackage {PARAMETERS-BOUND : bound} OPERATION-PACKAGE ::= {
--not impl     CONSUMER INVOKES    {furnishChargingInformation {bound}}
--not impl     ID      id-package-billing}
--not impl chargingPackage {PARAMETERS-BOUND : bound} OPERATION-PACKAGE ::= {
--not impl     CONSUMER INVOKES    {applyCharging {bound}}
--not impl     SUPPLIER INVOKES    {applyChargingReport {bound}}
--not impl     ID      id-package-charging}
--not impl trafficManagementPackage {PARAMETERS-BOUND : bound} OPERATION-PACKAGE ::= {
--not impl     CONSUMER INVOKES {callGap {bound}}
--not impl     ID id-package-trafficManagement}
--not impl callReportPackage {PARAMETERS-BOUND : bound} OPERATION-PACKAGE ::= {
--not impl     CONSUMER INVOKES    {callInformationRequest {bound}}
--not impl     SUPPLIER INVOKES    {callInformationReport {bound}}
--not impl     ID      id-package-callReport}
--not impl signallingControlPackage {PARAMETERS-BOUND : bound} OPERATION-PACKAGE ::= {
--not impl     CONSUMER INVOKES    {sendChargingInformation {bound}}
--not impl     ID      id-package-signallingControl}
--not impl activityTestPackage OPERATION-PACKAGE ::= {
--not impl     CONSUMER INVOKES    {activityTest}
--not impl     ID      id-package-activityTest}
--not impl cancelPackage {PARAMETERS-BOUND : bound} OPERATION-PACKAGE ::= {
--not impl     CONSUMER INVOKES    {cancel {bound}}
--not impl     ID      id-package-cancel}
--not impl 
--not impl 
--not impl 
-- Abstract Syntaxes
--not impl 
--not impl gsmSSF-scfGenericAbstractSyntax ABSTRACT-SYNTAX ::= {
--not impl     GenericSSF-gsmSCF-PDUs
--not impl     IDENTIFIED BY   id-as-gsmSSF-scfGenericAS}
--not impl GenericSSF-gsmSCF-PDUs ::= TCMessage {{SsfToScfGenericInvokable}, 
--not impl             {SsfToScfGenericReturnable}}
--not impl SsfScfGenericInvokable OPERATION ::= {
--not impl             activityTest |
--not impl             applyCharging {cAPSpecificBoundSet} |
--not impl             applyChargingReport {cAPSpecificBoundSet} |
--not impl             callInformationReport {cAPSpecificBoundSet} |
--not impl             callInformationRequest {cAPSpecificBoundSet} |
--not impl             cancel {cAPSpecificBoundSet} |
--not impl             connect {cAPSpecificBoundSet} |
--not impl             continueWithArgument {cAPSpecificBoundSet} |
--not impl             connectToResource {cAPSpecificBoundSet} |
--not impl             disconnectForwardConnection |
--not impl             establishTemporaryConnection {cAPSpecificBoundSet} | 
--not impl             eventReportBCSM {cAPSpecificBoundSet} |
--not impl             furnishChargingInformation {cAPSpecificBoundSet} |
--not impl             initialDP {cAPSpecificBoundSet} |
--not impl             releaseCall {cAPSpecificBoundSet} |
--not impl             requestReportBCSMEvent {cAPSpecificBoundSet} |
--not impl             resetTimer {cAPSpecificBoundSet} |
--not impl             sendChargingInformation {cAPSpecificBoundSet} |
--not impl             playAnnouncement {cAPSpecificBoundSet} |
--not impl             promptAndCollectUserInformation {cAPSpecificBoundSet} |
--not impl             specializedResourceReport
--not impl             }
--not impl SsfScfGenericReturnable OPERATION ::= {
--not impl             activityTest | 
--not impl             applyCharging {cAPSpecificBoundSet} | 
--not impl             applyChargingReport {cAPSpecificBoundSet} |
--not impl             callGap {networkSpecificBoundSet} |
--not impl             callInformationRequest {cAPSpecificBoundSet} |
--not impl             cancel {cAPSpecificBoundSet} | 
--not impl             connect {cAPSpecificBoundSet} | 
--not impl             connectToResource {cAPSpecificBoundSet} | 
--not impl             continue | 
--not impl             continueWithArgument {cAPSpecificBoundSet} |
--not impl             disconnectForwardConnection | 
--not impl             establishTemporaryConnection {cAPSpecificBoundSet}| 
--not impl             furnishChargingInformation {cAPSpecificBoundSet}| 
--not impl             initialDP {cAPSpecificBoundSet}|
--not impl             releaseCall {cAPSpecificBoundSet}| 
--not impl             requestReportBCSMEvent {cAPSpecificBoundSet}|
--not impl             resetTimer {cAPSpecificBoundSet}| 
--not impl             sendChargingInformation {cAPSpecificBoundSet}|
--not impl             playAnnouncement {cAPSpecificBoundSet}|
--not impl             promptAndCollectUserInformation {cAPSpecificBoundSet}
--not impl             }
--not impl 
--not impl assistHandoff-gsmSSF-scfAbstractSyntax ABSTRACT-SYNTAX ::= {
--not impl     AssistHandoffsSF-gsmSCF-PDUs
--not impl     IDENTIFIED BY   id-as-assistHandoff-gsmSSF-scfAS}
--not impl AssistHandoffsSF-gsmSCF-PDUs ::= TCMessage {{AssistHandoffssfToScfInvokable}, 
--not impl             {AssistHandoffssfToScfReturnable}}
--not impl AssistHandoffssfToScfInvokable OPERATION ::= {
--not impl             activityTest |
--not impl             assistRequestInstructions {cAPSpecificBoundSet}| 
--not impl             cancel {cAPSpecificBoundSet}| 
--not impl             connectToResource {cAPSpecificBoundSet}| 
--not impl             disconnectForwardConnection | 
--not impl             playAnnouncement {cAPSpecificBoundSet}| 
--not impl             promptAndCollectUserInformation {cAPSpecificBoundSet}| 
--not impl             resetTimer {cAPSpecificBoundSet}| 
--not impl             specializedResourceReport
--not impl             }
--not impl AssistHandoffssfToScfReturnable OPERATION ::= {
--not impl             activityTest |
--not impl             assistRequestInstructions {cAPSpecificBoundSet}| 
--not impl             cancel {cAPSpecificBoundSet}| 
--not impl             connectToResource {cAPSpecificBoundSet}| 
--not impl             disconnectForwardConnection | 
--not impl             playAnnouncement {cAPSpecificBoundSet}| 
--not impl             promptAndCollectUserInformation {cAPSpecificBoundSet}| 
--not impl             resetTimer {cAPSpecificBoundSet}
--not impl             }
--not impl 
--not impl END
--not impl 

--------------------------------------------------------------------------------
--------------------------------------------------------------------------------
--------------------------------------------------------------------------------


-- Module ----------------------------------------------------------------------
--------------------------------------------------------------------------------
-- CAP gsmSCF/gsmSRF Interface Operations and Arguments.
--------------------------------------------------------------------------------
--------------------------------------------------------------------------------
-- This module contains the operations and operation arguments used for the
-- gsmSRF - gsmSCF interface, for the control of circuit switched calls.

-- The table in subclause 2.1 lists the specifications that contain the modules
-- that are used by CAP.


-- Direction: gsmSCF -> gsmSRF, Timer: Tpa
-- This operation is to be used after Establish Temporary Connection (assist procedure
-- with a second gsmSSF) or a Connect to Resource (no assist) operation. It may be used
-- for inband interaction with a mobile station, or for interaction with an ISDN user.
-- In the former case, the gsmSRF is usually collocated with the gsmSSF for standard
-- tones (congestion tone...) or standard announcements.
-- In the latter case, the gsmSRF is always collocated with the gsmSSF in the switch.
-- Any error is returned to the gsmSCF. The timer associated with this operation must
-- be of a sufficient duration to allow its linked operation to be correctly correlated.

PlayAnnouncementArg --{PARAMETERS-BOUND : bound}--::= SEQUENCE {
	informationToSend					[0] InformationToSend --{bound}--,
	disconnectFromIPForbidden			[1] BOOLEAN DEFAULT TRUE,
	requestAnnouncementCompleteNotification	[2] BOOLEAN DEFAULT TRUE,
	extensions							[3] SEQUENCE SIZE(1.. -- bound.& -- numOfExtensions) OF 
                                                        ExtensionField   -- {bound} --  OPTIONAL,
	callSegmentID						[5] CallSegmentID --{bound}--					OPTIONAL,
	requestAnnouncementStartedNotification	[51] BOOLEAN DEFAULT FALSE,
	...
	}


-- Direction: gsmSCF -> gsmSRF, Timer: Tpc 
-- This operation is used to interact with a user to collect information.

PromptAndCollectUserInformationArg --{PARAMETERS-BOUND : bound}--::= SEQUENCE {
	collectedInfo						[0] CollectedInfo,
	disconnectFromIPForbidden			[1] BOOLEAN	DEFAULT TRUE,
	informationToSend					[2] InformationToSend --{bound}--				OPTIONAL,
	extensions							[3] SEQUENCE SIZE(1.. -- bound.& -- numOfExtensions) OF 
                                                        ExtensionField   -- {bound} --  OPTIONAL,
	callSegmentID						[4]	CallSegmentID --{bound}--					OPTIONAL,
	requestAnnouncementStartedNotification [51] BOOLEAN DEFAULT FALSE,
	...
	}

ReceivedInformationArg {PARAMETERS-BOUND : bound}::= CHOICE {
	digitsResponse						[0] Digits --{bound}--
	}


-- Direction: gsmSRF -> gsmSCF, Timer: Tsrr 
-- This operation is used as the response to a PlayAnnouncement operation when the announcement 
-- completed report indication is set.

SpecializedResourceReportArg ::= CHOICE {
	allAnnouncementsComplete			[50] NULL,
	firstAnnouncementStarted			[51] NULL
	}


--------------------------------------------------------------------------------
--------------------------------------------------------------------------------
--------------------------------------------------------------------------------


-- Module ----------------------------------------------------------------------
--------------------------------------------------------------------------------
-- CAP gsmSCF/gsmSCF Contracts, Packages and ACs.
--------------------------------------------------------------------------------
--------------------------------------------------------------------------------

-- This module specifies the Operation Packages, Contracts, Application Contexts
-- and Abstract Syntaxes used for the gsmSRF - gsmSCF interface, for the control of
-- circuit switched calls.

-- The table in subclause 2.1 lists the specifications that contain the modules
-- that are used by CAP.



--not impl 
--not impl CAP-gsmSCF-gsmSRF-pkgs-contracts-acs {ccitt(0) identified-organization(4) etsi(0) mobileDomain(0) umts-network(1)  modules(3) cAP-gsmSCF-gsmSRF-pkgs-contracts-acs(8) version3(2)}
--not impl 
--not impl DEFINITIONS ::= BEGIN
--not impl 
-- This module describes the operation-packages, contracts and application-contexts used
-- over the gsmSCF-gsmSRF interface.
--not impl 
--not impl IMPORTS
--not impl 
--not impl     PARAMETERS-BOUND,
--not impl     cAPSpecificBoundSet
--not impl FROM CAP-classes classes
--not impl 
--not impl     ROS-OBJECT-CLASS,
--not impl     CONTRACT,
--not impl     OPERATION-PACKAGE,
--not impl     OPERATION
--not impl FROM Remote-Operations-Information-Objects ros-InformationObjects
--not impl 
--not impl     TCMessage {} 
--not impl FROM TCAPMessages tc-Messages
--not impl 
--not impl     APPLICATION-CONTEXT,
--not impl     dialogue-abstract-syntax
--not impl FROM TC-Notation-Extensions tc-NotationExtensions
--not impl 
--not impl     playAnnouncement {},
--not impl     promptAndCollectUserInformation {},
--not impl     specializedResourceReport
--not impl FROM CAP-gsmSCF-gsmSRF-ops-args gsmSCF-gsmSRF-Operations
--not impl 
--not impl     activityTest,
--not impl     cancel {},
--not impl     assistRequestInstructions {}
--not impl FROM CAP-gsmSSF-gsmSCF-ops-args gsmSSF-gsmSCF-Operations
--not impl 
--not impl     gsmSRF-scfActivationOfAssistPackage {}
--not impl FROM CAP-gsmSSF-gsmSCF-pkgs-contracts-acs gsmSSF-gsmSCF-Protocol
--not impl 
--not impl     id-package-specializedResourceControl,
--not impl     id-ac-gsmSRF-gsmSCF,
--not impl     id-contract-gsmSRF-gsmSCF,
--not impl     id-package-gsmSRF-scfCancel,
--not impl     id-as-basic-gsmSRF-gsmSCF,
--not impl     classes,
--not impl     ros-InformationObjects,
--not impl     tc-Messages,
--not impl     tc-NotationExtensions,
--not impl     gsmSCF-gsmSRF-Operations,
--not impl     gsmSSF-gsmSCF-Operations,
--not impl     gsmSSF-gsmSCF-Protocol
--not impl FROM CAP-object-identifiers {ccitt(0) identified-organization(4) etsi(0) mobileDomain(0) umts-network(1) modules(3)  cAP-object-identifiers (17) version3(2)}
--not impl 
--not impl ;
--not impl 
-- Application Contexts 
--not impl 
--not impl gsmSRF-gsmSCF-ac APPLICATION-CONTEXT ::= {
--not impl     CONTRACT                    gsmSRF-gsmSCF-contract
--not impl     DIALOGUE MODE               structured
--not impl     TERMINATION                 basic
--not impl     ABSTRACT SYNTAXES           {dialogue-abstract-syntax | 
--not impl                                 gsmSRF-gsmSCF-abstract-syntax}
--not impl     APPLICATION CONTEXT NAME    id-ac-gsmSRF-gsmSCF}
--not impl 
-- Contracts 
--not impl 
--not impl gsmSRF-gsmSCF-contract CONTRACT ::= {
--not impl     INITIATOR CONSUMER OF       {gsmSRF-scfActivationOfAssistPackage {cAPSpecificBoundSet} }
--not impl     RESPONDER CONSUMER OF       {specializedResourceControlPackage {cAPSpecificBoundSet}|
--not impl                                 activityTestPackage {cAPSpecificBoundSet}|
--not impl                                 gsmSRF-scfCancelPackage {cAPSpecificBoundSet}}
--not impl     ID                          id-contract-gsmSRF-gsmSCF}
--not impl 
-- Operation Packages
--not impl 
--not impl specializedResourceControlPackage {PARAMETERS-BOUND : bound}  OPERATION-PACKAGE ::= {
--not impl     CONSUMER INVOKES    {playAnnouncement {bound} |
--not impl                         promptAndCollectUserInformation {bound}
--not impl     }
--not impl     SUPPLIER INVOKES    {specializedResourceReport}
--not impl     ID                  id-package-specializedResourceControl}
--not impl 
--not impl gsmSRF-scfActivationOfAssistPackage {PARAMETERS-BOUND : bound} OPERATION-PACKAGE ::= {
--not impl     CONSUMER INVOKES    {assistRequestInstructions {bound}}
--not impl     ID      id-package-gsmSRF-scfActivationOfAssist}
--not impl 
--not impl 
--not impl gsmSRF-scfCancelPackage {PARAMETERS-BOUND : bound}   OPERATION-PACKAGE ::= {
--not impl     CONSUMER INVOKES    {cancel {bound}}
--not impl     ID                  id-package-gsmSRF-scfCancel}
--not impl 
--not impl activityTestPackage {PARAMETERS-BOUND : bound}   OPERATION-PACKAGE ::= {
--not impl     CONSUMER INVOKES    {activityTest}
--not impl     ID                  id-package-activityTest}
--not impl 
-- Abstract Syntaxes 
--not impl 
--not impl gsmSRF-gsmSCF-abstract-syntax ABSTRACT-SYNTAX ::= {
--not impl     BASIC-gsmSRF-gsmSCF-PDUs
--not impl     IDENTIFIED BY   id-as-basic-gsmSRF-gsmSCF}
--not impl 
--not impl BASIC-gsmSRF-gsmSCF-PDUs ::= TCMessage {{GsmSRFgsmSCFInvokable},{GsmSRFgsmSCFReturnable}}
--not impl 
--not impl GsmSRFgsmSCFInvokable OPERATION ::= {
--not impl         activityTest |
--not impl         assistRequestInstructions  {cAPSpecificBoundSet}|
--not impl         cancel  {cAPSpecificBoundSet}|
--not impl         playAnnouncement  {cAPSpecificBoundSet}|
--not impl         promptAndCollectUserInformation  {cAPSpecificBoundSet}|
--not impl         specializedResourceReport 
--not impl         }
--not impl 
--not impl GsmSRFgsmSCFReturnable OPERATION ::= {
--not impl         activityTest |
--not impl         assistRequestInstructions  {cAPSpecificBoundSet}|
--not impl         cancel  {cAPSpecificBoundSet}|
--not impl         playAnnouncement  {cAPSpecificBoundSet}|
--not impl         promptAndCollectUserInformation  {cAPSpecificBoundSet}
--not impl         }
--not impl 
--not impl END
--not impl 

--------------------------------------------------------------------------------
--------------------------------------------------------------------------------
--------------------------------------------------------------------------------


-- Module ----------------------------------------------------------------------
--------------------------------------------------------------------------------
-- CAP SMS Operations and Arguments.
--------------------------------------------------------------------------------
--------------------------------------------------------------------------------

--not used 
--not used CAP-SMS-ops-args {ccitt(0) identified-organization(4) etsi(0) mobileDomain(0) umts-network(1) modules(3) cAP-SMS-ops-args(22) version3(2)}
--not used 
--not used DEFINITIONS IMPLICIT TAGS::= BEGIN
--not used 
--not used IMPORTS
--not used 
--not used     errortypes,
--not used     datatypes,
--not used     operationcodes,
--not used     classes,
--not used     ros-InformationObjects
--not used FROM CAP-object-identifiers {ccitt(0) identified-organization(4) etsi(0) mobileDomain(0)
--not used umts-network(1) modules(3) cAP-object-identifiers(17) version3(2)}
--not used 
--not used     OPERATION
--not used FROM Remote-Operations-Information-Objects ros-InformationObjects
--not used 
--not used     tc-Messages,
--not used     classes
--not used FROM CAP-object-identifiers {ccitt(0) identified-organization(4) etsi(0) mobileDomain(0)
--not used umts-network(1) modules(3) cAP-object-identifiers(17) version3(2)}
--not used 
--not used     ServiceKey
--not used FROM CS1-DataTypes { ccitt(0) identified-organization(4) etsi(0) mobileDomain(0)
--not used in-network(1) modules(0) cs1-datatypes(2) version1(0)}
--not used 
--not used     MiscCallInfo
--not used FROM CS2-datatypes { ccitt(0) identified-organization(4) etsi(0) mobileDomain(0) 
--not used in-network(1) cS2(20) modules(0) in-cs2-datatypes (0) version1(0)}
--not used 
--not used     IMSI,
--not used     ISDN-AddressString
--not used FROM MAP-CommonDataTypes {ccitt(0) identified-organization(4) etsi(0) mobileDomain(0)
--not used gsm-Network(1) modules(3) map-CommonDataTypes(18) version6(6)}
--not used 
--not used     LocationInformation
--not used FROM MAP-MS-DataTypes {ccitt(0) identified-organization(4) etsi(0) mobileDomain(0)
--not used gsm-Network(1) modules(3) map-MS-DataTypes(11) version6(6)}
--not used 
--not used     PARAMETERS-BOUND
--not used FROM CAP-classes classes
--not used 
--not used     opcode-activityTestSMS,
--not used     opcode-connectSMS,
--not used     opcode-continueSMS,
--not used     opcode-eventReportSMS,
--not used     opcode-furnishChargingInformationSMS,
--not used     opcode-initialDPSMS,
--not used     opcode-releaseSMS,
--not used     opcode-requestReportSMSEvent,
--not used     opcode-resetTimerSMS
--not used FROM CAP-operationcodes operationcodes
--not used 
--not used     CalledPartyBCDNumber {},
--not used     EventSpecificInformationSMS,
--not used     EventTypeSMS,
--not used     ExtensionField {},
--not used     FCISMSBillingChargingCharacteristics,
--not used     LocationInformationGPRS,
--not used     RPCause,
--not used     SMSEvent,
--not used     TimeAndTimezone {},
--not used     TimerID,
--not used     TimerValue,
--not used     TPDataCodingScheme,
--not used     TPProtocolIdentifier,
--not used     TPShortMessageSubmissionInfo,
--not used     TPValidityPeriod
--not used FROM CAP-datatypes datatypes
--not used 
--not used     missingCustomerRecord,
--not used     missingParameter,
--not used     parameterOutOfRange,
--not used     systemFailure,
--not used     taskRefused,
--not used     unexpectedComponentSequence,
--not used     unexpectedDataValue,
--not used     unexpectedParameter
--not used FROM CAP-errortypes errortypes
--not used 
--not used ;
--not used 
--not used activityTestSMS OPERATION ::= {
--not used     RETURN RESULT TRUE
--not used     CODE    opcode-activityTestSMS
--not used     }
-- Direction: gsmSCF -> gsmSSF/gprsSSF, Timer: Tatsms 
-- This operation is used to check for the continued existence of a relationship
-- between the gsmSCF and gsmSSF/gprsSSF. If the relationship is still in existence,
-- then the gsmSSF/gprsSSF will respond. If no reply is received, then the gsmSCF
-- will assume that the gsmSSF/gprsSSF has failed in some way.

--not used connectSMS {PARAMETERS-BOUND : bound} OPERATION ::= {
--not used     ARGUMENT
--not used         ConnectSMSArg {bound}
--not used     ERRORS {
--not used         MissingParameter |
--not used         ParameterOutOfRange |
--not used         SystemFailure |
--not used         TaskRefused |
--not used         UnexpectedComponentSequence |
--not used         UnexpectedDataValue |
--not used         unexpectedParameter
--not used         }
--not used     CODE opcode-connectSMS
--not used     }

--  Direction: gsmSCF -> gsmSSF or gprsSSF, Timer: Tconsms
--  This operation is used to request the smsSSF to perform the SMS processing
--  actions to route
--  or forward a short message to a specified destination.

ConnectSMSArg --{PARAMETERS-BOUND : bound}-- ::= SEQUENCE {
	callingPartysNumber					[0] ISDN-AddressString						OPTIONAL,
	destinationSubscriberNumber			[1] CalledPartyBCDNumber --{bound}--			OPTIONAL,
	sMSCAddress							[2] ISDN-AddressString						OPTIONAL,
	extensions							[10] SEQUENCE SIZE(1.. -- bound.& -- numOfExtensions) OF 
                                                        ExtensionField   -- {bound} --  OPTIONAL,
	...
	}


-- Direction: gsmSCF -> smsSSF, Timer: Tcuesms 
-- This operation is used to request the smsSSF to proceed with
-- Short Message processing at the DP at which it previously suspended
-- Short Message processing to await gsmSCF instructions (i.e. proceed
-- to the next Point in Association in the SMS FSM). The smsSSF
-- continues SMS processing without substituting new data from the gsmSCF.


--  Direction: gsmSSF or gprsSSF -> gsmSCF, Timer: Terbsms
--  This operation is used to notify the gsmSCF of a Short Message related event (FSM events
--  such as submission, delivery or failure) previously requested by the gsmSCF in a
--  RequestReportSMSEvent operation.

EventReportSMSArg --{PARAMETERS-BOUND : bound}-- ::= SEQUENCE {
	eventTypeSMS						[0] EventTypeSMS,
	eventSpecificInformationSMS			[1] EventSpecificInformationSMS				OPTIONAL,
	miscCallInfo						[2] MiscCallInfo --DEFAULT {messageType request}--,
	extensions							[10] SEQUENCE SIZE(1.. -- bound.& -- numOfExtensions) OF 
                                                        ExtensionField   -- {bound} --  OPTIONAL,
	...
	}


--  Direction: gsmSCF ?? gsmSSF or gprsSSF, Timer: Tfcisms 
--  This operation is used to request the smsSSF to generate, register a charging record
--  or to include some information in the default SM record. The registered charging record is
--  intended for off line charging of the Short Message.

FurnishChargingInformationSMSArg --{PARAMETERS-BOUND : bound}-- ::=
	FCISMSBillingChargingCharacteristics --{bound}--


-- Imported from cap v3
--

MSNetworkCapability                             ::= OCTET STRING (SIZE (3))
--  MS Network Capability describes the GPRS terminal capabilites related to the network, i.e. SMS
--  point to point service over packet data channels. For encoding refer to 3G TS 24.008 [12].

MSRadioAccessCapability                 ::= OCTET STRING (SIZE (3..32))
-- MS Radio Access Capability describes the terminal capabilites relevant for the radio network, 
-- which may affect the way the network handles the mobile.
-- For encoding refer to 3G TS 24.008 [12].

GPRSMSClass                                 ::= SEQUENCE    {
        mSNetworkCapability                 [0] MSNetworkCapability,
        mSRadioAccessCapability             [1] MSRadioAccessCapability
        }
-- GPRS MS class mark describes the terminal capabilites.
-- For encoding refer to 3G TS 24.008 [12].


--  Direction: gsmSSF or gprsSSF -> gsmSCF, Timer: Tidpsms
--  This operation is used after a TDP to indicate request for service.

InitialDPSMSArg --{PARAMETERS-BOUND : bound}-- ::= SEQUENCE {
	serviceKey							[0] ServiceKey,
	destinationSubscriberNumber			[1] CalledPartyBCDNumber --{bound}--			OPTIONAL,
	callingPartyNumber					[2] ISDN-AddressString						OPTIONAL,
	eventTypeSMS						[3] EventTypeSMS							OPTIONAL,
	iMSI								[4] IMSI									OPTIONAL,
	locationInformationMSC				[5] LocationInformation						OPTIONAL,
	locationInformationGPRS				[6] LocationInformationGPRS					OPTIONAL,
	sMSCAddress							[7] ISDN-AddressString						OPTIONAL,
	timeAndTimezone						[8] TimeAndTimezone --{bound}--					OPTIONAL,
	tPShortMessageSpecificInfo			[9] TPShortMessageSpecificInfo				OPTIONAL,
	tPProtocolIdentifier				[10] TPProtocolIdentifier					OPTIONAL,
	tPDataCodingScheme					[11] TPDataCodingScheme						OPTIONAL,
	tPValidityPeriod					[12] TPValidityPeriod						OPTIONAL,
	extensions							[13] SEQUENCE SIZE(1.. -- bound.& -- numOfExtensions) OF 
                                                        ExtensionField   -- {bound} --  OPTIONAL,
	...,
	smsReferenceNumber					[14] CallReferenceNumber					OPTIONAL,
	mscAddress							[15] ISDN-AddressString						OPTIONAL,
	sgsn-Number							[16] ISDN-AddressString						OPTIONAL,
	ms-Classmark2						[17] MS-Classmark2							OPTIONAL,
	gPRSMSClass 						[18] GPRSMSClass							OPTIONAL,
	iMEI								[19] IMEI									OPTIONAL,
	calledPartyNumber					[17] ISDN-AddressString						OPTIONAL
	}


--  Direction: gsmSCF -> gsmSSF or gprsSSF, Timer: Trelsms
--  This operation is used to prevent an attempt to submit or deliver a short message. 

ReleaseSMSArg ::= RPCause


--  Direction: gsmSCF -> gsmSSF or gprsSSF, Timer: Trrbsms
--  This operation is used to request the gsmSSF or gprsSSF to monitor for a
--  Short Message related event (FSM events such as submission, delivery or failure)
--  and to send a notification to the gsmSCF when the event is detected.

RequestReportSMSEventArg --{PARAMETERS-BOUND : bound}-- ::= SEQUENCE {
	sMSEvents							[0] SEQUENCE SIZE (1..--bound.&--numOfSMSEvents) OF SMSEvent,
	extensions							[10] SEQUENCE SIZE(1.. -- bound.& -- numOfExtensions) OF 
                                                        ExtensionField   -- {bound} --  OPTIONAL,
	...
	}
--  Indicates the Short Message related events(s) for notification.


-- Direction: gsmSCF -> smsSSF, Timer: Trtsms 
-- This operation is used to request the smsSSF to refresh an application
-- timer in the smsSSF.

ResetTimerSMSArg --{PARAMETERS-BOUND : bound}-- ::= SEQUENCE {
	timerID								[0] TimerID	DEFAULT tssf,
	timervalue							[1] TimerValue,
	extensions							[2] SEQUENCE SIZE(1.. -- bound.& -- numOfExtensions) OF 
                                                        ExtensionField   -- {bound} --  OPTIONAL,
	...
	}


--------------------------------------------------------------------------------
--------------------------------------------------------------------------------
--------------------------------------------------------------------------------


-- Module ----------------------------------------------------------------------
--------------------------------------------------------------------------------
-- CAP SMS Contracts, Packages and ACs.
--------------------------------------------------------------------------------
--------------------------------------------------------------------------------

-- This module specifies the Operation Packages, Contracts, Application Contexts
-- and Abstract Syntaxes used for the smsSSF - gsmSCF interface, for the
-- control of MO-SMS and MT-SMS.

-- The table in subclause 2.1 lists the specifications that contain the modules
-- that are used by CAP.

--not impl 
--not impl CAP-smsSSF-gsmSCF-pkgs-contracts-acs {ccitt(0) identified-organization(4) etsi(0) mobileDomain(0) umts-network(1) modules(3) cAP-smsSSF-gsmSCF-pkgs-contracts-acs(23) version3(2)}
--not impl 
--not impl DEFINITIONS ::= BEGIN
--not impl 
-- This module describes the operation-packages, contracts and application-contexts used
-- over the gsmSSF/gprsSSF-gsmSCF interface.
--not impl 
--not impl IMPORTS
--not impl 
--not impl     PARAMETERS-BOUND,
--not impl     cAPSpecificBoundSet
--not impl FROM CAP-classes classes 
--not impl 
--not impl 
--not impl     ROS-OBJECT-CLASS,
--not impl     CONTRACT,
--not impl     OPERATION-PACKAGE,
--not impl     OPERATION
--not impl FROM Remote-Operations-Information-Objects ros-InformationObjects
--not impl 
--not impl     TCMessage {} 
--not impl FROM TCAPMessages tc-Messages
--not impl 
--not impl     APPLICATION-CONTEXT,
--not impl     dialogue-abstract-syntax
--not impl FROM TC-Notation-Extensions tc-NotationExtensions
--not impl 
--not impl     activityTestSMS,
--not impl     connectSMS{},
--not impl     continueSMS,
--not impl     eventReportSMS{},
--not impl     furnishChargingInformationSMS{},
--not impl     initialDPSMS{},
--not impl     releaseSMS,
--not impl     requestReportSMSEvent{},
--not impl     resetTimerSMS{}
--not impl FROM CAP-SMS-ops-args sms-Operations
--not impl 
--not impl     sms-Operations,
--not impl     tc-NotationExtensions,
--not impl     tc-Messages,
--not impl     ros-InformationObjects,
--not impl     classes,
--not impl     id-as-sms-AS 
--not impl FROM CAP-object-identifiers {ccitt(0) identified-organization(4) etsi(0) mobileDomain(0)
--not impl umts-network(1) modules(3) cAP-object-identifiers (17) version3(2)}
--not impl 
--not impl ;
--not impl 
-- Application Contexts
--not impl 
--not impl cap3-sms-AC APPLICATION-CONTEXT ::= {
--not impl     CONTRACT                    cap3SMS
--not impl     DIALOGUE MODE               structured
--not impl     ABSTRACT SYNTAXES           {dialogue-abstract-syntax |
--not impl                                 gprsSSF-scfAbstractSyntax} 
--not impl     APPLICATION CONTEXT NAME    id-ac-cap3-sms-AC}
--not impl 
--not impl 
-- Contracts
--not impl 
--not impl cap3SMS CONTRACT ::= {
-- dialogue initiated by gprsSSF or gsmSSF with InitialDPSMS Operation
--not impl     INITIATOR CONSUMER OF   
--not impl             {smsActivationPackage {cAPSpecificBoundSet}}
--not impl     RESPONDER CONSUMER OF
--not impl             {smsConnectPackage {cAPSpecificBoundSet} |
--not impl             smsReleasePackage {cAPSpecificBoundSet} |
--not impl             smsEventHandlingPackage {cAPSpecificBoundSet} |
--not impl             smsTimerPackage {cAPSpecificBoundSet} |
--not impl             smsBillingPackage {cAPSpecificBoundSet} |
--not impl             smsProcessingPackage {cAPSpecificBoundSet} |
--not impl             smsActivityTestPackage {cAPSpecificBoundSet}
--not impl cAPSpecificBoundSetcAPSpecificBoundSet}
--not impl     ID      id-cap3GprsSsfToScf
--not impl     }
--not impl 
--not impl 
-- Operation Packages
--not impl 
--not impl smsActivationPackage {PARAMETERS-BOUND : bound}  OPERATION-PACKAGE ::= {
--not impl     CONSUMER INVOKES    {initialDPSMS {bound}}
--not impl     ID      id-package-smsActivation}
--not impl smsConnectPackage {PARAMETERS-BOUND : bound} OPERATION-PACKAGE ::= {
--not impl     CONSUMER INVOKES    {connectSMS {bound}}
--not impl     ID      id-package-smsConnect}
--not impl smsProcessingPackage {PARAMETERS-BOUND : bound} OPERATION-PACKAGE ::= {
--not impl     CONSUMER INVOKES    {continueSMS}
--not impl     ID      id-package-smsContinue}
--not impl smsReleasePackage  {PARAMETERS-BOUND : bound} OPERATION-PACKAGE ::= {
--not impl     CONSUMER INVOKES    {releaseSMS }
--not impl     ID      id-package-smsRelease}
--not impl smsEventHandlingPackage {PARAMETERS-BOUND : bound} OPERATION-PACKAGE ::= {
--not impl     CONSUMER INVOKES    {requestReportSMSEvent {bound}}
--not impl     SUPPLIER INVOKES    {eventReportSMS {bound}}
--not impl     ID      id-package-smsEventHandling}
--not impl smsBillingPackage {PARAMETERS-BOUND : bound} OPERATION-PACKAGE ::= {
--not impl     CONSUMER INVOKES    {furnishChargingInformationSMS {bound}}
--not impl     ID      id-package-smsBilling}
--not impl smsActivityTestPackage OPERATION-PACKAGE ::= {
--not impl     CONSUMER INVOKES    {activityTestSMS}
--not impl     ID      id-package-smsActivityTest}
--not impl smsTimerPackage {PARAMETERS-BOUND : bound} OPERATION-PACKAGE ::= {
--not impl     CONSUMER INVOKES    {resetTimerSMS {bound}}
--not impl     ID      id-package-smsTimer}
--not impl 
--not impl 
--not impl 
-- Abstract Syntaxes
--not impl 
--not impl sms-AbstractSyntax ABSTRACT-SYNTAX ::= {
--not impl     Generic-sms-PDUs
--not impl     IDENTIFIED BY   id-as-sms-AS}
--not impl 
--not impl Generic-sms-PDUs ::= TCMessage {{SmsInvokable}, 
--not impl             {SmsReturnable}}
--not impl 
--not impl SmsInvokable OPERATION ::= {
--not impl     activityTestSMS |
--not impl     connectSMS {cAPSpecificBoundSet} |
--not impl     eventReportSMS {cAPSpecificBoundSet} |
--not impl     furnishChargingInformationSMS {cAPSpecificBoundSet} |
--not impl     initialDPSMS {cAPSpecificBoundSet} |
--not impl     requestReportSMSEvent {cAPSpecificBoundSet} |
--not impl     resetTimerSMS {cAPSpecificBoundSet}
--not impl     }
--not impl 
--not impl SmsReturnable OPERATION ::= {
--not impl     activityTestSMS | 
--not impl     connectSMS {cAPSpecificBoundSet} | 
--not impl     continueSMS | 
--not impl     furnishChargingInformationSMS {cAPSpecificBoundSet}| 
--not impl     initialDPSMS {cAPSpecificBoundSet}|
--not impl             releaseSMS {cAPSpecificBoundSet}| 
--not impl             requestReportSMSEvent {cAPSpecificBoundSet}|
--not impl             resetTimerSMS {cAPSpecificBoundSet} 
--not impl             }
--not impl 
--not impl END
--not impl 

--------------------------------------------------------------------------------
--------------------------------------------------------------------------------
--------------------------------------------------------------------------------


-- Module ----------------------------------------------------------------------
--------------------------------------------------------------------------------
-- CAP gsmSCF/gprsSSF Operations and Arguments.
--------------------------------------------------------------------------------
--------------------------------------------------------------------------------

-- Direction: gsmSCF -> gprsSSF, Timer: Tatg
-- This operation is used to check for the continued existence of a relationship between the gsmSCF 
-- and gprsSSF. If the relationship is still in existence, then the gprsSSF will respond. If no 
-- reply is received, then the gsmSCF will assume that the gprsSSF has failed in some way
-- and will take the appropriate action.


-- Direction gsmSCF -> gprsSSF, Timer Tacg
-- This operation is used for interacting from the gsmSCF with the gprsSSF CSE-controlled 
-- GPRS session or PDP Context charging mechanism.

ApplyChargingGPRSArg ::= SEQUENCE { 
	chargingCharacteristics				[0] ChargingCharacteristics,
	tariffSwitchInterval				[1] INTEGER (1..86400)						OPTIONAL,
	pDPID								[2] PDPID									OPTIONAL,
	...
	}
-- tariffSwitchInterval is measured in 1 second units.


--	Direction gprsSSF -> gsmSCF,Timer Tacrg
--	The ApplyChargingReportGPRS operation provides the feedback from the gprsSCF to the gsmSCF 
--	CSE-controlled GPRS session charging mechanism.

ApplyChargingReportGPRSArg ::= SEQUENCE {
	chargingResult						[0] ChargingResult,
	qualityOfService					[1] QualityOfService						OPTIONAL,
	active								[2] BOOLEAN DEFAULT TRUE,
	pDPID								[3] PDPID									OPTIONAL,
	...,
	chargingRollOver					[4]	ChargingRollOver						OPTIONAL
	}


--  Direction: gsmSCF ?? gprsSSF, Timer: Tcag
--  This generic operation cancels all previous requests, 
--	i.e. all EDPs and reports can be cancelled by the gsmSCF.

CancelGPRSArg ::= SEQUENCE {
	pDPID								[0] PDPID 									OPTIONAL,
	...
	}


-- Direction: gsmSCF -> gprsSSF, Timer: Tcong
-- This operation is used to modify the Access Point Name used when establishing a PDP Context.

ConnectGPRSArg --{PARAMETERS-BOUND: bound}--::= SEQUENCE {
	accessPointName		[0] AccessPointName --{bound}--,
	pdpID		[1] PDPID			OPTIONAL,
	...
	}


--  Direction: gsmSCF -> gprsSSF, Timer: Tcueg
--  This operation is used to request the gprsSSF to proceed with processing at the DP at 
--  which it previously suspended processing to await gsmSCF instructions (i.e., proceed to 
--  the next point in processing in the Attach/Detach state model or PDP Context
--	state model) substituting new data from the gsmSCF.

ContinueGPRSArg ::= SEQUENCE {
	pDPID								[0] PDPID									OPTIONAL,
	...
}


--  Direction: gprsSSF -> gsmSCF, Timer: Terg
--  This operation is used when the GPRS Session is detached or a PDP Context is diconnected and
--  the associated event is not armed for reporting.
--  The usage of this operation is independent of the functional entity that initiates the Detach
--  or PDP Context Disconnection and is independent of the cause of the Detach or PDP Context
--  Disconnect.

EntityReleasedGPRSArg --{PARAMETERS-BOUND : bound}-- ::= SEQUENCE {
	gPRSCause							[0] GPRSCause --{bound}--,
	pDPID								[1] PDPID									OPTIONAL,
	...
	}


--	Direction gprsSSF -> gsmSCF,Timer Tereg
--		This operation is used to notify the gsmSCF of a GPRS session or PDP context related 
--		events (e.g. PDP context activation) previously requested by the gsmSCF in a 
--		RequestReportGPRSEventoperation.

EventReportGPRSArg --{PARAMETERS-BOUND : bound}--::= SEQUENCE {
	gPRSEventType						[0] GPRSEventType,
	miscGPRSInfo						[1] MiscCallInfo --DEFAULT {messageType request}--,
	gPRSEventSpecificInformation		[2]	GPRSEventSpecificInformation --{bound}--	OPTIONAL,
	pDPID								[3]	PDPID OPTIONAL,
	...
	}


-- Direction: gsmSCF -> gprsSSF, Timer: Tfcig 
-- This operation is used to request the gprsSSF to generate, register a logical record or to 
-- include some information in the default logical GPRS record.
-- The registered logical record is intended for off line charging of the GPRS session
-- or PDP Context.

FurnishChargingInformationGPRSArg --{PARAMETERS-BOUND : bound}-- ::=
	FCIGPRSBillingChargingCharacteristics--{bound}--


--	Direction gprsSSF -> gsmSCF,Timer Tidpg
--	This operation is used by the gprsSSF when a trigger is detected at a DP in the GPRS state
--	machines to request instructions from the gsmSCF

RAIdentity                                  ::= OCTET STRING (SIZE (6))
--  Routing Area Identity coded according to 3G TS 29.060 [43].

InitialDPGPRSArg --{PARAMETERS-BOUND : bound}--::= SEQUENCE {
	serviceKey							[0] ServiceKey,
	gPRSEventType						[1] GPRSEventType,
	mSISDN								[2] ISDN-AddressString,
	iMSI								[3] IMSI,
	timeAndTimeZone						[4] TimeAndTimezone --{bound}--,
	gPRSMSClass							[5] GPRSMSClass								OPTIONAL,
	endUserAddress						[6] EndUserAddress --{bound}--					OPTIONAL,
	qualityOfService					[7] QualityOfService						OPTIONAL,
	accessPointName						[8] AccessPointName--{bound}--					OPTIONAL,
	routeingAreaIdentity				[9] RAIdentity								OPTIONAL,
	chargingID							[10] GPRSChargingID							OPTIONAL,
	sGSNCapabilities					[11] SGSNCapabilities						OPTIONAL,
	locationInformationGPRS				[12] LocationInformationGPRS				OPTIONAL,
	pDPInitiationType					[13] PDPInitiationType						OPTIONAL,
	extensions							[14] SEQUENCE SIZE(1.. -- bound.& -- numOfExtensions) OF 
                                                        ExtensionField   -- {bound} --  OPTIONAL,
	...,
	gGSNAddress							[15] GSN-Address							OPTIONAL,
	secondaryPDP-context				[16] NULL									OPTIONAL,
	iMEI								[17] IMEI									OPTIONAL
	}
--	The RouteingAreaIdentity parameter is not used. 
--	The receiving entity shall ignore RouteingAreaIdentity if received.
--  The RouteingAreaIdentity is conveyed in the LocationInformationGPRS parameter.


--  Direction: gsmSCF -> gprsSSF, Timer: Trg
--  This operation is used to tear down an existing GPRS session or PDP Context at any phase.

ReleaseGPRSArg --{PARAMETERS-BOUND : bound}-- ::= SEQUENCE {
	gprsCause							[0] GPRSCause --{bound}--,
	pDPID								[1]	PDPID									OPTIONAL,
	...
	}

-- Direction: gsmSCF -> gprsSSF, Timer: Trrqe
-- This operation is used to request the gprsSSF to monitor for an event (e.g., GPRS events 
-- such as attach or PDP Context activiation), then send a notification back to the 
-- gsmSCF when the event is detected.

RequestReportGPRSEventArg --{PARAMETERS-BOUND : bound}-- ::= SEQUENCE {
	gPRSEvents							[0] SEQUENCE SIZE (1..--bound.&--numOfGPRSEvents) OF GPRSEvent,
	pDPID								[1]	PDPID									OPTIONAL,
	...
	}
-- Indicates the GPRS related events for notification.


--  Direction: gsmSCF -? gprsSSF, Timer: Trtg 
--  This operation is used to request the gprsSSF to refresh an application timer in the gprsSSF.

ResetTimerGPRSArg ::= SEQUENCE {
	timerID								[0] TimerID					DEFAULT tssf,
	timervalue							[1] TimerValue,
	...
	}


-- Direction: gsmSCF -> gprsSSF, Timer: Tscig 
-- This operation is used to instruct the gprsSSF on the charging information which the 
-- gprsSSF shall send to the Mobile Station by means of GSM access signalling.

SendChargingInformationGPRSArg --{PARAMETERS-BOUND: bound}--::= SEQUENCE {
	sCIGPRSBillingChargingCharacteristics [0] SCIGPRSBillingChargingCharacteristics --{ bound}--,
	...
	}

--not used 
--not used END
--not used 

--------------------------------------------------------------------------------
--------------------------------------------------------------------------------
--------------------------------------------------------------------------------


-- Module ----------------------------------------------------------------------
--------------------------------------------------------------------------------
-- CAP gsmSCF/gprsSSF Contracts, Packages and ACs.
--------------------------------------------------------------------------------
--------------------------------------------------------------------------------



--------------------------------------------------------------------------------
--------------------------------------------------------------------------------
--------------------------------------------------------------------------------


-- Module ----------------------------------------------------------------------
--------------------------------------------------------------------------------
-- CAP gsmSCF/gprsSSF Contracts, Packages and ACs.
--------------------------------------------------------------------------------
--------------------------------------------------------------------------------
--not impl 
--not impl CAP-gprsSSF-gsmSCF-pkgs-contracts-acs {ccitt(0) identified-organization(4) etsi(0) mobileDomain(0) umts-network(1) modules(3) cAP-gprsSSF-gsmSCF-pkgs-contracts-acs (25) version3(2)}
--not impl 
--not impl DEFINITIONS ::= BEGIN
--not impl 
-- This module describes the operation-packages, contracts and application-contexts used
-- over the gprsSSF-gsmSCF interface.
--not impl 
--not impl IMPORTS
--not impl 
--not impl     PARAMETERS-BOUND,
--not impl     cAPSpecificBoundSet
--not impl FROM CAP-classes classes 
--not impl 
--not impl     ROS-OBJECT-CLASS,
--not impl     CONTRACT,
--not impl     OPERATION-PACKAGE,
--not impl     OPERATION
--not impl FROM Remote-Operations-Information-Objects ros-InformationObjects
--not impl 
--not impl     TCMessage {} 
--not impl FROM TCAPMessages tc-Messages
--not impl 
--not impl     APPLICATION-CONTEXT,
--not impl     dialogue-abstract-syntax
--not impl FROM TC-Notation-Extensions tc-NotationExtensions
--not impl 
--not impl     ActivityTestGPRS {},
--not impl     applyChargingGPRS {},
--not impl     applyChargingReportGPRS {},
--not impl     cancelGPRS {},
--not impl     connectGPRS {},
--not impl     continueGPRS {},
--not impl     entityReleasedGPRS {},
--not impl     furnishChargingInformationGPRS {},
--not impl     initialDPGPRS {},
--not impl     releaseGPRS {},
--not impl     eventReportGPRS {},
--not impl     requestReportGPRSEvent {},
--not impl     resetTimerGPRS {},
--not impl     sendChargingInformationGPRS {}
--not impl FROM CAP-gprsSSF-gsmSCF-ops-args gprsSSF-gsmSCF-Operations
--not impl 
--not impl     id-ac-CAP-gprsSSF-gsmSCF-AC,
--not impl     id-cap3GprsSsfTogsmScf,
--not impl     id-as-gprsSSF-gsmSCF-AS,
--not impl     id-as-gsmSCF-gprsSSF-AS,
--not impl     classes,
--not impl     ros-InformationObjects,
--not impl     tc-Messages,
--not impl     tc-NotationExtensions,
--not impl     gprsSSF-gsmSCF-Operations
--not impl FROM CAP-object-identifiers {ccitt(0) identified-organization(4) etsi(0) mobileDomain(0)
--not impl umts-network(1) modules(3) cAP-object-identifiers (17) version3(2)}
--not impl 
--not impl ;
--not impl 
--not impl 
-- Application Contexts
--not impl 
--not impl cap3-gprssf-scfAC APPLICATION-CONTEXT ::= {
--not impl     CONTRACT                    cap3GprsSsfToScf
--not impl     DIALOGUE MODE               structured
--not impl     ABSTRACT SYNTAXES           {dialogue-abstract-syntax |
--not impl                                 gprsSSF-fgsmSCFAbstractSyntax} 
--not impl     APPLICATION CONTEXT NAME    id-ac-CAP-gprsSSF-gsmSCF-AC}
--not impl 
--not impl cap3-gsmscf-gprsssfAC APPLICATION-CONTEXT ::= {
--not impl     CONTRACT                    cap3GsmScfToGprsSsf
--not impl     DIALOGUE MODE               structured
--not impl     ABSTRACT SYNTAXES           {dialogue-abstract-syntax |
--not impl                                 gsmSCF-gprsSSFAbstractSyntax} 
--not impl     APPLICATION CONTEXT NAME    id-ac-CAP-gsmSCF-gprsSSF-AC }
--not impl 
--not impl 
-- Contracts
--not impl 
--not impl cap3GprsSsfToScf CONTRACT ::= {
-- dialogue initiated by gprsSSF with InitialDPGPRS, ApplyChargingReportGPRS,
-- EntityReleaseGPRS and EventReportGPRS Operations
--not impl     INITIATOR CONSUMER OF   
--not impl             {
--not impl             gprSscfActivationPackage {cAPSpecificBoundSet} |
--not impl             gprsEventHandlingPackage {cAPSpecificBoundSet} |
--not impl             gprsChargingPackage {cAPSpecificBoundSet} |
--not impl             gprsExceptionInformationPackage
--not impl             }
--not impl     RESPONDER CONSUMER OF
--not impl             {
--not impl             gprsConnectPackage {cAPSpecificBoundSet} |
--not impl             gprsProcessingPackage {cAPSpecificBoundSet} |
--not impl             gprsReleasePackage {cAPSpecificBoundSet} |
--not impl             gprsEventHandlingPackage {cAPSpecificBoundSet} |
--not impl             gprsTimerPackage {cAPSpecificBoundSet} |
--not impl             gprsBillingPackage {cAPSpecificBoundSet} |
--not impl             gprsChargingPackage {cAPSpecificBoundSet} |
--not impl             gprsCancelPackage {cAPSpecificBoundSet} |
--not impl             gprsChargeAdvicePackage {cAPSpecificBoundSet}
--not impl             }
--not impl     ID      id-cap3GprsSsfTogsmScf
--not impl     }
--not impl 
--not impl cap3GsmScfToGprsSsf CONTRACT ::= {
-- dialogue initiated by gsmSCF with ApplyCharginGPRS, ActivityTestGPRS,
-- CancelGPRS, FurnishChargingInformationGPRS, ReleaseGPRS,
-- RequestReportGPRSEvent and SendChargingInformationGPRS Operations
--not impl     INITIATOR CONSUMER OF   
--not impl     {
--not impl             gprsReleasePackage {networkSpecificBoundSet} |
--not impl             gprsEventHandlingPackage {networkSpecificBoundSet} |
--not impl             gprsTimerPackage {networkSpecificBoundSet} |
--not impl             gprsBillingPackage {networkSpecificBoundSet} |
--not impl             gprsChargingPackage {networkSpecificBoundSet} |
--not impl             gprsActivityTestPackage {networkSpecificBoundSet} |
--not impl             gprsCancelPackage {networkSpecificBoundSet} |
--not impl             gprsChargeAdvicePackage {networkSpecificBoundSet}
--not impl     }
--not impl     RESPONDER CONSUMER OF
--not impl     {
--not impl     }
--not impl     ID      id-cap3GprsSsfTogsmScf
--not impl     }
--not impl 
--not impl 
-- Operation Packages
--not impl 
--not impl gprsScfActivationPackage {PARAMETERS-BOUND : bound}  OPERATION-PACKAGE ::= {
--not impl     CONSUMER INVOKES    { initialDPGPRS {bound}}
--not impl     ID      id-package-gprsScfActivation}
--not impl gprsConnectPackage {PARAMETERS-BOUND : bound} OPERATION-PACKAGE ::= {
--not impl     CONSUMER INVOKES    {connectGPRS {bound}}
--not impl     ID      id-package-gprsConnect}
--not impl gprsProcessingPackage {PARAMETERS-BOUND : bound} OPERATION-PACKAGE ::= {
--not impl     CONSUMER INVOKES    {continueGPRS {bound}}
--not impl     ID      id-package-gprsContinue}
--not impl gprsReleasePackage  {PARAMETERS-BOUND : bound} OPERATION-PACKAGE ::= {
--not impl     CONSUMER INVOKES    {releaseGPRS {bound}}
--not impl     ID      id-package-gprsRelease}
--not impl gprsEventHandlingPackage {PARAMETERS-BOUND : bound} OPERATION-PACKAGE ::= {
--not impl     CONSUMER INVOKES    {requestReportGPRSEvent {bound}}
--not impl     SUPPLIER INVOKES    {eventReportGPRS {bound}}
--not impl     ID      id-package-gprsEventHandling}
--not impl gprsExceptionInformationPackage {PARAMETERS-BOUND : bound} OPERATION-PACKAGE ::= {
--not impl     CONSUMER INVOKES    {entityReleasedGPRS {bound}}
--not impl     ID      id-package-gprsExceptionInformation}
--not impl gprsTimerPackage {PARAMETERS-BOUND : bound} OPERATION-PACKAGE ::= {
--not impl     CONSUMER INVOKES    {resetTimerGPRS {bound}}
--not impl     ID      id-package-gprsTimer}
--not impl gprsBillingPackage {PARAMETERS-BOUND : bound} OPERATION-PACKAGE ::= {
--not impl     CONSUMER INVOKES    {furnishChargingInformationGPRS {bound}}
--not impl     ID      id-package-gprsBilling}
--not impl gprsChargingPackage {PARAMETERS-BOUND : bound} OPERATION-PACKAGE ::= {
--not impl     CONSUMER INVOKES    {applyChargingGPRS {bound}}
--not impl     SUPPLIER INVOKES    {applyChargingReportGPRS {bound}}
--not impl     ID      id-package-gprsCharging}
--not impl gprsChargeAdvicePackage {PARAMETERS-BOUND : bound} OPERATION-PACKAGE ::= {
--not impl     CONSUMER INVOKES    {sendChargingInformationGPRS {bound}}
--not impl     ID      id-package-gprsChargeAdvice}
--not impl gprsActivityTestPackage OPERATION-PACKAGE ::= {
--not impl     CONSUMER INVOKES    {activityTestGPRS {bound}}
--not impl     ID      id-package-gprsActivityTest}
--not impl gprsCancelPackage {PARAMETERS-BOUND : bound} OPERATION-PACKAGE ::= {
--not impl     CONSUMER INVOKES    {cancelGPRS {bound}}
--not impl     ID      id-package-gprsCancel}
--not impl 
--not impl 
--not impl 
-- Abstract Syntaxes
--not impl 
--not impl gprsSSF-gsmSCFAbstractSyntax ABSTRACT-SYNTAX ::= {
--not impl     GenericGprsSSF-gsmSCF-PDUs
--not impl     IDENTIFIED BY   id-as-gprsSSF-gsmSCF-AS}
--not impl 
--not impl GenericGprsSSF-gsmSCF-PDUs ::= TCMessage {{GprsSsfToGsmScfInvokable}, 
--not impl             {GprsSsfToGsmScfReturnable}}
--not impl 
--not impl GprsSsfToGsmScfGenericInvokable OPERATION ::= {
--not impl             activityTestGPRS {networkSpecificBoundSet} |
--not impl             applyChargingGPRS {cAPSpecificBoundSet} |
--not impl             applyChargingReportGPRS {cAPSpecificBoundSet} |
--not impl             cancelGPRS {cAPSpecificBoundSet} |
--not impl             connectGPRS {cAPSpecificBoundSet} |
--not impl             entityReleasedGPRS {cAPSpecificBoundSet} | 
--not impl             eventReportGPRS {cAPSpecificBoundSet} |
--not impl             furnishChargingInformationGPRS {cAPSpecificBoundSet} |
--not impl             initialDPGPRS {cAPSpecificBoundSet} |
--not impl             releaseGPRS {cAPSpecificBoundSet} |
--not impl             requestReportGPRSEvent {cAPSpecificBoundSet} |
--not impl             resetTimerGPRS {cAPSpecificBoundSet} |
--not impl             sendChargingInformationGPRS {cAPSpecificBoundSet}
--not impl             }
--not impl 
--not impl GprsSsfToGsmScfReturnable OPERATION ::= {
--not impl             activityTestGPRS {networkSpecificBoundSet} |
--not impl             applyChargingGPRS {cAPSpecificBoundSet} | 
--not impl             applyChargingReportGPRS {cAPSpecificBoundSet} | 
--not impl             cancelGPRS {cAPSpecificBoundSet} | 
--not impl             connectGPRS {cAPSpecificBoundSet} | 
--not impl             continueGPRS {cAPSpecificBoundSet} |
--not impl             entityReleasedGPRS {cAPSpecificBoundSet} |
--not impl             furnishChargingInformationGPRS {cAPSpecificBoundSet}| 
--not impl             initialDPGPRS {cAPSpecificBoundSet}|
--not impl             releaseGPRS {cAPSpecificBoundSet}| 
--not impl             requestReportGPRSEvent {cAPSpecificBoundSet}|
--not impl             resetTimerGPRS {cAPSpecificBoundSet}| 
--not impl             sendChargingInformationGPRS {cAPSpecificBoundSet}
--not impl             }
--not impl 
--not impl gsmSCF-gprsSSFGenericAbstractSyntax ABSTRACT-SYNTAX ::= {
--not impl     GenericGsmSCF-gprsSSF-PDUs
--not impl     IDENTIFIED BY   id-as-gsmSCF-gprsSSF-AS}
--not impl 
--not impl GenericGsmSCF-gprsSSF-PDUs ::= TCMessage {{GsmScfToGprsSsfInvokable}, {GsmScfToGprsSsfReturnable}}
--not impl 
--not impl GsmScfToGprsSsfInvokable OPERATION ::= {
--not impl             activityTestGPRS {networkSpecificBoundSet} |
--not impl             applyChargingGPRS {cAPSpecificBoundSet}| 
--not impl             cancelGPRS {cAPSpecificBoundSet}| 
--not impl             furnishChargingInformationGPRS {cAPSpecificBoundSet}| 
--not impl             releaseGPRS {cAPSpecificBoundSet}| 
--not impl             requestReportGPRSEvent {cAPSpecificBoundSet}|
--not impl             sendChargingInformationGPRS {cAPSpecificBoundSet} 
--not impl             }
--not impl 
--not impl GsmScfToGprsSsfReturnable OPERATION ::= {
--not impl             activityTestGPRS {networkSpecificBoundSet} |
--not impl             applyChargingGPRS {cAPSpecificBoundSet}| 
--not impl             cancelGPRS {cAPSpecificBoundSet}| 
--not impl             furnishChargingInformationGPRS {cAPSpecificBoundSet}| 
--not impl             releaseGPRS {cAPSpecificBoundSet}| 
--not impl             requestReportGPRSEvent {cAPSpecificBoundSet}| 
--not impl             sendChargingInformationGPRS {cAPSpecificBoundSet} 
--not impl             }
--not impl 
--not impl END
--not impl 

--------------------------------------------------------------------------------
--------------------------------------------------------------------------------
--------------------------------------------------------------------------------


--------------------------------------------------------------------------------
--------------------------------------------------------------------------------
-- Added global module definition (end).
--------------------------------------------------------------------------------
--------------------------------------------------------------------------------

END

--------------------------------------------------------------------------------
--------------------------------------------------------------------------------
