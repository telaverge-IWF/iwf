-------------------------------------------------------------------------------
--                                                                           --
--      Copyright 2002 IntelliNet Technologies, Inc. All Rights Reserved.    --
--              Manufactured in the United States of America.                --
--        1990 W. New Haven Ste. 312, Melbourne, Florida, 32904 U.S.A.       --
--                                                                           --
--    This product and related documentation is protected by copyright and   --
--    distributed under licenses restricting its use, copying, distribution  --
--    and decompilation.  No part of this product or related documentation   --
--    may be reproduced in any form by any means without prior written       --
--    authorization of IntelliNet Technologies and its licensors, if any.    --
--                                                                           --
--    RESTRICTED RIGHTS LEGEND:  Use, duplication, or disclosure by the      --
--    government is subject to restrictions as set forth in subparagraph     --
--    (c)(1)(ii) of the Rights in Technical Data and Computer Software       --
--    clause at DFARS 252.227-7013 and FAR 52.227-19.                        --
--                                                                           --
-------------------------------------------------------------------------------
--                                                                           --
--  CONTRACT: INTERNAL                                                       --
--                                                                           --
-------------------------------------------------------------------------------
--
--  ID: $Id: inap_eric_lrf.asn,v 9.2 2008/04/22 11:33:38 kramesh Exp $
--
-------------------------------------------------------------------------------

-------------------------------------------------------------------------------
-------------------------------------------------------------------------------
--
--  ASN.1 Module for INAP ETSI CS-1 from Ericsson.
--
--  LRF (Local Reference Format) version (from recommendation).
--
-------------------------------------------------------------------------------
-------------------------------------------------------------------------------

--
-- From file: Abstract Syntax - FS 156 155 17-APR 101 15 Uen B.doc
--


--------------------------------------------------------------------------------
--------------------------------------------------------------------------------


INAP-ERICSSON

DEFINITIONS IMPLICIT TAGS ::=

BEGIN


--Core-INAP-CS1-Errors { ccitt(0) identified-organization(4) etsi(0) inDomain(1) in-network(1) modules(0)
--cs1-errors(1) version1(0)}
-- This module contains the type definitions for the IN CS1 errors.
--DEFINITIONS IMPLICIT TAGS ::=
--BEGIN
--IMPORTS
--ERROR
--FROM TCAPMessages {ccitt recommendation q 773 modules(2) messages(1) version2(2)}
--InvokeID,
--UnavailableNetworkResource
--FROM Core-INAP-CS1-DataTypes {ccitt(0) identified-organization(4) etsi(0) inDomain(1) in-network(1)
--modules(0) cs1-datatypes(2) version1(0)};
-- TYPE DEFINITIONS FOR IN CS1 ERRORS FOLLOW
--Cancelled ::= ERROR
-- The operation has been cancelled.
CancelFailed ::= --ERROR
--PARAMETER-- SEQUENCE {
problem [0] ENUMERATED {
unknownOperation(0),
tooLate(1),
operationNotCancellable(2)
},
operation [1] InvokeID
}
-- The operation failed to be cancelled.
--ETCFailed ::= ERROR
-- The establish temporary connection failed.
--ImproperCallerResponse ::= ERROR
-- The caller response was not as expected.
--MissingCustomerRecord ::= ERROR
-- The Service Logic Program (SLP) could not be found in the SCF.
--MissingParameter ::= ERROR
-- An expected optional parameter was not received.
--ParameterOutOfRange ::= ERROR
-- The parameter was not as expected (e.g., missing or out of range).
RequestedInfoError ::= --ERROR
--PARAMETER-- ENUMERATED {
unknownRequestedInfo(1),
requestedInfoNotAvailable(2)
}
-- The requested information cannot be found.
--SystemFailure ::= ERROR
--PARAMETER
--UnavailableNetworkResource
-- The operation could not be completed due to a system failure at the serving PE.

TaskRefused ::= --ERROR
--PARAMETER-- ENUMERATED {
generic(0),
unobtainable(1),
congestion(2)
}
-- An entity normally capable of the task requested cannot or chooses not to perform the task at
-- this time (this includes error situations like congestion and unobtainable address as used in
-- e.g., the connect operation).
--UnavailableResource ::= ERROR
-- A requested resource is not available at the serving entity.
--UnexpectedComponentSequence ::= ERROR
-- An incorrect sequence of Components was received (e.g., "DisconnectForwardConnection"
-- followed by "PlayAnnouncement").
--UnexpectedDataValue ::= ERROR
-- The data value was not as expected (e.g., routing number expected but billing number
-- received)
--UnexpectedParameter ::= ERROR
-- A parameter received was not expected.
--UnknownLegID ::= ERROR
-- Leg not known to the SSF.
--END
--


--EXTENSION MACRO ::=
--BEGIN
--TYPE NOTATION ::= ExtensionType Criticality
--VALUE NOTATION ::= value(INTEGER)
--ExtensionType ::= "EXTENSION-SYNTAX" type
--Criticality ::= "CRITICALITY" value(CriticalityType)
--CriticalityType ::= ENUMERATED {
--ignore(0),
--abort(1)
--}
--END
-- Example of addition of an extension named "SomeNetworkSpecificIndicator" of type
-- BOOLEAN, with criticality "abort" and to be identified as extension number 1
-- Example of definition using the above macro:
--
-- SomeNetworkSpecificIndicator ::= EXTENSION
-- EXTENSION SYNTAX BOOLEAN
-- CRITICALITY abort
--
-- someNetworkSpecificIndicator SomeNetworkSpecificIndicator ::= 1
--
-- Example of transfer syntax, using the ExtensionField datatype as specified in the module
-- below. Assuming the value of the extension is set to TRUE, the extensions parameter
-- becomes a SEQUENCE of type INTEGER ::= 1, criticality ENUMERATED ::= 1 and
-- value [1] IMPLICIT BOOLEAN ::= TRUE.


--Core-INAP-CS1-DataTypes {ccitt(0) identified-organization(4) etsi(0) inDomain(1) in-network(1) modules(0)
--cs1-datatypes(2) version1(0)}
-- This module contains the type definitions for the IN CS1 data types.
-- The following parameters map onto bearer protocol (i.e., ETS 300 403-1 [8] (DSS1) and
-- ETS 300 356-1 [7] (ISUP)) parameters:
-- CalledPartyNumber, BearerCapability, CallingPartyNumber, HighLayerCompatibility,
-- DestinationRoutingAddress, OriginalCalledPartyID, RedirectingPartyID, RedirectionInformation,
-- AccessTransport, CallingPartyCategory, ForwardCallIndicators, LocationNumber,
-- AssistingSSPIPRoutingAddress, AlertingPattern (Q.931 only), ReleaseCause
-- (and other Cause parameters), AdditionalCallingPartyNumber.
-- The following SSF parameters do not map onto bearer protocol (i.e., ETS 300 403-1 [8] (DSS1)
-- and ETS 300 356-1 [7] (ISUP)) parameters and therefore are assumed to be local to the
-- switching system:
-- RouteList, LegID, IPSSPCapabilities, IPAvailable, CGEncountered,
-- CorrelationID, Timers, MiscCallInfo, and ServiceKey.
-- Where possible, administrations should specify within their network the maximum size of
-- parameters specified in this ETS that are of an indeterminate length.
--DEFINITIONS IMPLICIT TAGS ::=
--BEGIN
--IMPORTS
--InvokeIdType
--FROM TCAPMessages {ccitt recommendation q 773 modules(2) messages(1) version2(2)};
-- TYPE DEFINITIONS FOR IN CS1 DATA TYPES FOLLOW
-- Argument Data Types
-- The ordering of parameters in the argument sequences has been arbitrary. Further study may
-- be required to order arguments in a manner which will facilitate efficient encoding and decoding.

ActivateServiceFilteringArg ::= SEQUENCE {
    filteredCallTreatment    [0] FilteredCallTreatment,
    filteringCharacteristics [1] FilteringCharacteristics,
    filteringTimeOut         [2] FilteringTimeOut,
    filteringCriteria        [3] FilteringCriteria,
    startTime                [4] DateAndTime OPTIONAL,
    extensions               [5] SEQUENCE SIZE(1..7) OF ExtensionField OPTIONAL
}

ApplyChargingArg ::= SEQUENCE {
    aChBillingChargingCharacteristics [0] AChBillingChargingCharacteristics,
    sendCalculationToSCPIndication    [1] BOOLEAN DEFAULT TRUE,
    partyToCharge      [2] SendingSideID OPTIONAL,
    extensions         [3] SEQUENCE SIZE(1..7) OF ExtensionField OPTIONAL
}

ApplyChargingReportArg ::= CallResult

AssistRequestInstructionsArg ::= SEQUENCE {
    correlationID     [0] GenericNumber,
    iPSSPCapabilities [2] IPSSPCapabilities OPTIONAL,
    extensions        [3] SEQUENCE SIZE(1..7) OF ExtensionField OPTIONAL
}

CallGapArg ::= SEQUENCE {
    gapCriteria   [0] GapCriteria,
    gapIndicators [1] GapIndicators,
    controlType   [2] ControlType OPTIONAL,
    gapTreatment  [3] GapTreatment OPTIONAL,
    extensions    [4] SEQUENCE SIZE(1..7) OF ExtensionField OPTIONAL
}

CallInformationReportArg ::= SEQUENCE {
    requestedInformationList [0] RequestedInformationList,
    extensions               [2] SEQUENCE SIZE(1..7) OF ExtensionField OPTIONAL
}

CallInformationRequestArg ::= SEQUENCE {
    requestedInformationTypeList [0] RequestedInformationTypeList,
    extensions                   [2] SEQUENCE SIZE(1..7) OF ExtensionField OPTIONAL
}

CancelArg ::= CHOICE {
    invokeID    [0] InvokeID,
    allRequests [1] NULL
}

CollectInformationArg ::= SEQUENCE {
    extensions [4] SEQUENCE SIZE(1..7) OF ExtensionField OPTIONAL
}

ConnectArg ::= SEQUENCE {
    destinationRoutingAddress [0] DestinationRoutingAddress,
    alertingPattern           [1] AlertingPattern OPTIONAL,
    correlationID             [2] GenericDigits OPTIONAL,
    cutAndPaste               [3] CutAndPaste OPTIONAL,
    originalCalledPartyID     [6] Number OPTIONAL,
    routeList                 [7] RouteList OPTIONAL,
    sCFID                     [8] GenericNumber OPTIONAL,
    extensions                [10] SEQUENCE SIZE(1..7) OF ExtensionField OPTIONAL,
    serviceInteractionIndicators [26] CONServiceInteractionIndicators OPTIONAL,
    callingPartyNumber           [27] Number OPTIONAL,
    callingPartysCategory        [28] CallingPartysCategory OPTIONAL,
    redirectingPartyID           [29] Number OPTIONAL,
    redirectionInformation       [30] RedirectionInformation OPTIONAL
}

ConnectToResourceArg ::= SEQUENCE {
    resourceAddress CHOICE {
    ipRoutingAddress [0] IPRoutingAddress,
    none             [3] NULL
    },
    extensions                   [4] SEQUENCE SIZE(1..7) OF ExtensionField OPTIONAL,
    serviceInteractionIndicators [30] CTRServiceInteractionIndicators OPTIONAL
}

EstablishTemporaryConnectionArg ::= SEQUENCE {
    assistingSSPIPRoutingAddress [0] GenericNumber,
    correlationID                [1] GenericDigits OPTIONAL,
    sCFID                        [3] GenericNumber OPTIONAL,
    extensions                   [4] SEQUENCE SIZE(1..7) OF ExtensionField OPTIONAL,
    serviceInteractionIndicators [30] ETCServiceInteractionIndicators OPTIONAL
}

EventNotificationChargingArg ::= SEQUENCE {
    eventTypeCharging         [0] EventTypeCharging,
    eventSpecificInfoCharging [1] EventSpecificInfoCharging OPTIONAL,
    legID                     [2] ReceivingSideID OPTIONAL,
    extensions                [3] SEQUENCE SIZE(1..7) OF ExtensionField OPTIONAL,
    monitorMode               [30] MonitorMode DEFAULT notifyAndContinue
}

EventReportBCSMArg ::= SEQUENCE {
    eventTypeBCSM [0] EventTypeBCSM,
    eventSpecificInformationBCSM [2] EventSpecificInformationBCSM OPTIONAL,
    legID [3] ReceivingSideID OPTIONAL,
    miscCallInfo [4] MiscCallInfo DEFAULT(
                "MiscCallInfo* miscCallInfo = new MiscCallInfo(&staticDesc);
                MiscCallInfo::MessageType* messageType = new MiscCallInfo::MessageType((long)0);
                miscCallInfo->SetMessageType(messageType);
                staticDesc.SetCloneForDefaultFactory(miscCallInfo);"), -- {messageType request},
    extensions [5] SEQUENCE SIZE(1..7) OF ExtensionField OPTIONAL
}

FurnishChargingInformationArg ::= FCIBillingChargingCharacteristics

InitialDPArg ::= SEQUENCE {
    serviceKey                   [0] ServiceKey,
    calledPartyNumber            [2] Number OPTIONAL,
    callingPartyNumber           [3] Number OPTIONAL,
    callingPartysCategory        [5] CallingPartysCategory OPTIONAL,
    cGEncountered                [7] CGEncountered OPTIONAL,
    iPSSPCapabilities            [8] IPSSPCapabilities OPTIONAL,
    locationNumber               [10] Number OPTIONAL,
    originalCalledPartyID        [12] Number OPTIONAL,
    extensions                   [15] SEQUENCE SIZE(1..16) OF ExtensionField OPTIONAL,
    highLayerCompatibility       [23] HighLayerCompatibility OPTIONAL,
    serviceInteractionIndicators [24] IDPServiceInteractionIndicators OPTIONAL,
    additionalCallingPartyNumber [25] GenericNumber OPTIONAL,
    forwardCallIndicators        [26] ForwardCallIndicators OPTIONAL,
    bearerCapability             [27] BearerCapability OPTIONAL,
    eventTypeBCSM                [28] EventTypeBCSM OPTIONAL,
    redirectingPartyID           [29] Number OPTIONAL,
    redirectionInformation       [30] RedirectionInformation OPTIONAL
}

InitiateCallAttemptArg ::= SEQUENCE {
    destinationRoutingAddress    [0] DestinationRoutingAddress,
    alertingPattern              [1] AlertingPattern OPTIONAL,
    extensions                   [4] SEQUENCE SIZE(1..7) OF ExtensionField OPTIONAL,
    serviceInteractionIndicators [29] ICAServiceInteractionIndicators OPTIONAL,
    callingPartyNumber           [30] Number OPTIONAL
}

PlayAnnouncementArg ::= SEQUENCE {
    informationToSend           [0] InformationToSend,
    disconnectFromIPForbidden   [1] BOOLEAN DEFAULT TRUE,
    requestAnnouncementComplete [2] BOOLEAN DEFAULT TRUE,
    extensions                  [3] SEQUENCE SIZE(1..16) OF ExtensionField OPTIONAL
}

PromptAndCollectUserInformationArg ::= SEQUENCE {
    collectedInfo             [0] CollectedInfo,
    disconnectFromIPForbidden [1] BOOLEAN DEFAULT TRUE,
    informationToSend         [2] InformationToSend OPTIONAL,
    extensions                [3] SEQUENCE SIZE(1..16) OF ExtensionField OPTIONAL
}

ReceivedInformationArg ::= CHOICE {
    digitsResponse [0] GenericDigits
}

ReleaseCallArg ::= Cause

RequestNotificationChargingEventArg ::= SEQUENCE SIZE (1..3) OF ChargingEvent

RequestReportBCSMEventArg ::= SEQUENCE {
    bcsmEvents [0] SEQUENCE SIZE (1..11) OF BCSMEvent,
    extensions [2] SEQUENCE SIZE (1..7) OF ExtensionField OPTIONAL
}

ResetTimerArg ::= SEQUENCE {
    timerID    [0] TimerID DEFAULT tssf,
    timervalue [1] TimerValue,
    extensions [2] SEQUENCE SIZE(1..7) OF ExtensionField OPTIONAL
}

SendChargingInformationArg ::= SEQUENCE {
    sCIBillingChargingCharacteristics [0] SCIBillingChargingCharacteristics,
    legID                             [1] SendingSideID,
    extensions                        [2] SEQUENCE SIZE(1..7) OF ExtensionField OPTIONAL
}

ServiceFilteringResponseArg ::= SEQUENCE {
    countersValue     [0] CountersValue,
    filteringCriteria [1] FilteringCriteria
}

SpecializedResourceReportArg ::= NULL

-- Common Data Types
AChBillingChargingCharacteristics ::= SEQUENCE {
    reportCondition     [0] ReportCondition,
    requestedReportInfo [1] RequestedReportInfo
}

ReportCondition ::= CHOICE {
    reportAtEndOfConnection [1] NULL,
    reportAtChargeLimit     [2] INTEGER (0..32767),
    reportImmediately       [3] NULL
}

RequestedReportInfo  ::= SEQUENCE {
    accumulatedCharge       [0] NULL    OPTIONAL,
    actualTariff            [1] NULL    OPTIONAL,
    tariffChangeInformation [2] NULL    OPTIONAL,
    chargeableDuration      [3] NULL    OPTIONAL,
    timeOfAnswer            [4] NULL    OPTIONAL
}

AlertingPattern ::= OCTET STRING (SIZE (3))

BackwardServiceInteractionIndicators ::= SEQUENCE {
    conferenceTreatmentIndicator   [1] OCTET STRING (SIZE(1)) OPTIONAL,
    callTransferTreatmentIndicator [193] OCTET STRING (SIZE(1)) OPTIONAL
}

BCSMEvent ::= SEQUENCE {
    eventTypeBCSM      [0] EventTypeBCSM,
    monitorMode        [1] MonitorMode,
    legID              [2] SendingSideID OPTIONAL,
    dPSpecificCriteria [30] DPSpecificCriteria OPTIONAL
}

DPSpecificCriteria ::= CHOICE {
    numberOfDigits   [0] INTEGER (1..28),
    applicationTimer [1] INTEGER (0..2047)
}

BearerCapability ::= CHOICE {
    bearerCap [0] OCTET STRING (SIZE (2..11)),
    tmr     [1]     OCTET STRING (SIZE(1))
}

BothwayThroughConnectIndicator ::= ENUMERATED {
    bothwayPathRequired           (0),
    bothwayPathNotRequired        (1)
}

CallingPartysCategory ::= OCTET STRING (SIZE (1))

CallResult ::= OCTET STRING (SIZE (16 .. 97))

CallResultDetails ::= SEQUENCE {
   reportCondition         [0] RepCondition,
   timeStamp               [1] DateAndTime,
   partyToCharge           [2] ReceivingSideID,
   accumulatedCharge       [3] INTEGER (0..65535) OPTIONAL,
   actualTariff            [4] TariffInformation OPTIONAL,
   tariffChangeInformation [5] SEQUENCE SIZE(1..4) OF TariffInformation OPTIONAL,
   chargeableDuration      [6] INTEGER (0..2147483647) OPTIONAL, 
   timeOfAnswer            [7] DateAndTime OPTIONAL
}

RepCondition ::= ENUMERATED {
    endOfConnection (1),
    chargeLimit     (2),
    immediately     (3)
}

Cause ::= OCTET STRING (SIZE (2))

CGEncountered ::= ENUMERATED {
    manualCGencountered(1),
    sCPOverload(2)
}

ChargingAnalysisInputData ::= SEQUENCE {
    chargingOrigin      [1] OCTET STRING (SIZE (1)) OPTIONAL,
    trafficActivityCode [2] OCTET STRING (SIZE (4))   OPTIONAL,
    chargingCode        [3] INTEGER (0..4095) OPTIONAL
}
 
ChargingEvent ::= SEQUENCE {
    eventTypeCharging [0] EventTypeCharging,
    monitorMode       [1] MonitorMode,
    legID             [2] SendingSideID OPTIONAL
}

CollectedDigits ::= SEQUENCE {
    minimumNumberOfDigits [0] INTEGER (1..28) DEFAULT 1,
    maximumNumberOfDigits [1] INTEGER (1..28),
    endOfReplyDigit       [2] OCTET STRING (SIZE (1..2)) OPTIONAL,
    cancelDigit           [3] OCTET STRING (SIZE (1..2)) OPTIONAL,
    startDigit            [4] OCTET STRING (SIZE (1..2)) OPTIONAL,
    firstDigitTimeOut     [5] INTEGER (1..127) OPTIONAL,
    interDigitTimeOut     [6] INTEGER (1..127) OPTIONAL,
    errorTreatment        [7] ErrorTreatment DEFAULT stdErrorAndInfo,
    interruptableAnnInd   [8] BOOLEAN DEFAULT TRUE,
    voiceInformation      [9] BOOLEAN DEFAULT FALSE,
    voiceBack             [10] BOOLEAN DEFAULT FALSE
}

CollectedInfo ::= CHOICE {
    collectedDigits [0] CollectedDigits
}

ConnectedNumberTreatmentIndicator ::= ENUMERATED {
    noINImpact (0),
    presentationRestricted (1),
    presentCalledINNumber (2)
}

CONServiceInteractionIndicators ::= SEQUENCE {
    forwardServiceInteractionIndicators  [0] ForwardServiceInteractionIndicators OPTIONAL,
    backwardServiceInteractionIndicators [1] BackwardServiceInteractionIndicators OPTIONAL,
    suspendTimer                         [3] SuspendTimer OPTIONAL,
    connectedNumberTreatmentIndicator    [4] ConnectedNumberTreatmentIndicator OPTIONAL
}
 
ControlType ::= ENUMERATED {
    sCPOverloaded(0),
    manuallyInitiated(1)
}

CounterAndValue ::= SEQUENCE {
    counterID    [0] INTEGER (0..99),
    counterValue [1] INTEGER (0..2147483647)
}

CountersValue ::= SEQUENCE SIZE(0..100) OF CounterAndValue

CTRServiceInteractionIndicators ::= SEQUENCE {
    backwardServiceInteractionIndicators [1] BackwardServiceInteractionIndicators OPTIONAL,
    bothwayThroughConnectIndicator       [2] BothwayThroughConnectIndicator OPTIONAL,
    connectedNumberTreatmentIndicator    [4] ConnectedNumberTreatmentIndicator OPTIONAL
}
 
CutAndPaste ::= INTEGER (0..22)

DateAndTime ::= OCTET STRING (SIZE(6))

DestinationRoutingAddress ::= SEQUENCE SIZE (1) OF Number

ElementaryMessageID ::= INTEGER (0..65535)

ErrorTreatment ::= ENUMERATED {
    stdErrorAndInfo(0),
    help(1),
    repeatPrompt(2)
}

ETCServiceInteractionIndicators ::= SEQUENCE {
    backwardServiceInteractionIndicators [1] BackwardServiceInteractionIndicators OPTIONAL,
    bothwayThroughConnectIndicator       [2] BothwayThroughConnectIndicator OPTIONAL,
    connectedNumberTreatmentIndicator    [4] ConnectedNumberTreatmentIndicator OPTIONAL
}

EventSpecificInformationBCSM ::= CHOICE {
    collectedInfoSpecificInfo      [0] SEQUENCE {
        calledPartyNumber [0] Number
    },
    analyzedInfoSpecificInfo       [1] SEQUENCE {
        calledPartyNumber [0] Number
    },
    routeSelectFailureSpecificInfo [2] SEQUENCE {
        failureCause [0] Cause OPTIONAL
    },
    oCalledPartyBusySpecificInfo   [3] SEQUENCE {
        busyCause [0] Cause OPTIONAL
    },
    oNoAnswerSpecificInfo          [4] SEQUENCE {
    },
    oAnswerSpecificInfo            [5] SEQUENCE {
    },
    oMidCallSpecificInfo           [6] SEQUENCE {
    },
    oDisconnectSpecificInfo        [7] SEQUENCE {
        releaseCause [0] Cause OPTIONAL
    },
    tCalledPartyBusySpecificInfo   [8] SEQUENCE {
        busyCause [0] Cause OPTIONAL
    },
    tNoAnswerSpecificInfo          [9] SEQUENCE {
    },
    tAnswerSpecificInfo            [10] SEQUENCE {
    },
    tMidCallSpecificInfo           [11] SEQUENCE {
    },
    tDisconnectSpecificInfo        [12] SEQUENCE {
        releaseCause [0] Cause OPTIONAL
    }
}

EventSpecificInfoCharging ::= CHOICE {
    tariffInformation        [0] TariffInformation,
    tariffIndicator          [1] OCTET STRING (SIZE(2)),
    chargeNoChargeIndication [2] ChargeNoChargeIndication
}

EventTypeBCSM ::= ENUMERATED {
    origAttemptAuthorized(1),
    collectedInfo(2),
    analyzedInformation(3),
    routeSelectFailure(4),
    oCalledPartyBusy(5),
    oNoAnswer(6),
    oAnswer(7),
    oMidCall(8),
    oDisconnect(9),
    oAbandon(10),
    termAttemptAuthorized(12),
    tCalledPartyBusy(13),
    tNoAnswer(14),
    tAnswer(15),
    tMidCall(16),
    tDisconnect(17),
    tAbandon(18)
}

EventTypeCharging ::= ENUMERATED {
    tariffInformation         (1),
    tariffIndicator           (2),
    chargeNoChargeIndication  (3)
}

ExtensionField ::= SEQUENCE {
    type INTEGER (0..63), 
    criticality ENUMERATED {
        ignore(0),
        abort(1)
    } DEFAULT ignore,
    value [1] ANY DEFINED BY type
}

FCIBillingChargingCharacteristics ::= OCTET STRING (SIZE (5..794))

FCIBillingDetails ::= SEQUENCE {
    partyToCharge            [1] SendingSideID,
    createINBillingRecord    [2] NULL OPTIONAL,
    additionalBillingInfo    [3] AdditionalBillingInfo OPTIONAL,
    tariffInformation        [4] TariffInformation OPTIONAL,
    startOfChargingIndicator [5] StartOfChargingIndicator OPTIONAL,
    orderStartOfCharging     [6] NULL OPTIONAL,
    chargingChangeIndicator  [7] ChargingChangeIndicator OPTIONAL
}

AdditionalBillingInfo ::= SEQUENCE {
    chargeParty            [0] ChargeParty OPTIONAL,
    serviceFeatureCode     [1] OCTET STRING (SIZE(2)) OPTIONAL,
    chargingUnitsAddition  [2] INTEGER (0..32767) OPTIONAL,
    genericChargingDigits  [3] GenericDigitsSet OPTIONAL,
    genericChargingNumbers [4] GenericNumberSet OPTIONAL
}

ChargeParty ::= CHOICE {
    single      [0] Single,
    distributed [1] Distributed
}

Single ::= ENUMERATED {
    aPartyToBeCharged     (0),
    bPartyToBeCharged     (1),
    cPartyToBeCharged     (2),
    otherPartyToBeCharged (3)
}

Distributed ::= SEQUENCE SIZE (4) OF INTEGER (0..99)

StartOfChargingIndicator ::= ENUMERATED {
    atResourceConnection (0),
    atAnswer             (1),
    whenOrdered          (2)
}

ChargingChangeIndicator ::= ENUMERATED {
    resumeCharging (1),
    holdCharging   (2)
}

FilteredCallTreatment ::= SEQUENCE {
    sFBillingChargingCharacteristics [0] SFBillingChargingCharacteristics,
    informationToSend                [1] InformationToSend OPTIONAL,
    maximumNumberOfCounters          [2] INTEGER (1..100)  DEFAULT 1,
    releaseCause                     [3] Cause OPTIONAL
}

FilteringCharacteristics ::= CHOICE {
    interval      [0] INTEGER (-1..32000),
    numberOfCalls [1] INTEGER (0..65535)
}

FilteringCriteria ::= CHOICE {
    serviceKey        [2] ServiceKey,
    addressAndService [30] SEQUENCE {
        calledAddressValue  [0] GenericNumber,
        serviceKey          [1] ServiceKey,
        callingAddressValue [2] GenericNumber OPTIONAL,
        locationNumber      [3] Number OPTIONAL
    }
}

FilteringTimeOut ::= CHOICE {
    duration [0] INTEGER (-1..86400),
    stopTime [1] DateAndTime
}

ForwardCallIndicators ::= OCTET STRING (SIZE (2))

ForwardServiceInteractionIndicators ::= SEQUENCE {
    conferenceTreatmentIndicator    [1] OCTET STRING (SIZE(1)) OPTIONAL,
    callDiversionTreatmentIndicator [2] OCTET STRING (SIZE(1)) OPTIONAL,
    callOfferingTreatmentIndicator  [3] OCTET STRING (SIZE(1)) OPTIONAL,
    callTransferTreatmentIndicator  [193] OCTET STRING (SIZE(1)) OPTIONAL
}

GapCriteria ::= CHOICE {
    calledAddressValue       [0] GenericNumber,
    gapOnService             [2] GapOnService,
    calledAddressAndService  [29] SEQUENCE {
        calledAddressValue [0] GenericNumber,
        serviceKey         [1] ServiceKey
    },
    callingAddressAndService [30] SEQUENCE {
        callingAddressValue [0] GenericNumber,
        serviceKey          [1] ServiceKey,
        locationNumber      [2] Number OPTIONAL
    }
}

GapOnService ::= SEQUENCE {
    serviceKey [0] ServiceKey
}

GapIndicators ::= SEQUENCE {
    duration    [0] INTEGER (-1..86400),
    gapInterval [1] INTEGER (-1..60000)
}

GapTreatment ::= CHOICE {
    informationToSend [0] InformationToSend,
    releaseCause      [1] Cause,
    both              [2] SEQUENCE {
        informationToSend [0] InformationToSend,
        releaseCause      [1] Cause
    }
}

GenericDigits ::= OCTET STRING (SIZE(2..15))

GenericDigitsSet ::= SET SIZE (1..20) OF GenericDigits

GenericNumber ::= OCTET STRING (SIZE(3..17))

GenericNumberSet ::= SET SIZE (1..20) OF GenericNumber

HighLayerCompatibility ::= OCTET STRING (SIZE(2))

ICAServiceInteractionIndicators ::= SEQUENCE {
    forwardServiceInteractionIndicators [0] ForwardServiceInteractionIndicators OPTIONAL,
    suspendTimer                        [3] SuspendTimer OPTIONAL
}

IDPServiceInteractionIndicators ::= SEQUENCE {
    forwardServiceInteractionIndicators  [0] ForwardServiceInteractionIndicators OPTIONAL,
    backwardServiceInteractionIndicators [1] BackwardServiceInteractionIndicators OPTIONAL
}

InbandInfo ::= SEQUENCE {
    messageID           [0] MessageID,
    numberOfRepetitions [1] INTEGER (1..127) OPTIONAL,
    duration            [2] INTEGER (0..32767) OPTIONAL,
    interval            [3] INTEGER (0..32767) OPTIONAL
}

InformationToSend ::= CHOICE {
    inbandinfo         [0] InbandInfo,
    tone               [1] Tone,
    displayInformation [2] DisplayInformation
}

Tone ::= SEQUENCE {
    toneID   [0] INTEGER (0..65535),
    duration [1] INTEGER (0..127) OPTIONAL
}

DisplayInformation ::= IA5String (SIZE (1..127))

InvokeID ::= INTEGER (-128..127)

IPRoutingAddress ::= Number

IPSSPCapabilities ::= OCTET STRING (SIZE (2))

LegType ::= INTEGER (1..2)

MessageID ::= CHOICE {
    elementaryMessageID [0] ElementaryMessageID,
    variableMessage     [30] SEQUENCE {
        elementaryMessageID [0] ElementaryMessageID,
        variableParts       [1] SEQUENCE SIZE(1..5) OF VariablePart
    }
}

VariablePart ::= CHOICE {
    integer                  [0] INTEGER (0..65535),
    number                   [1] GenericDigits, -- Generic digits
    time                     [2] OCTET STRING (SIZE(2)), -- HH:MM, BCD coded
    date                     [3] OCTET STRING (SIZE(3)), -- YYMMDD, BCD coded
    priceInHundredthsOfUnits [4] OCTET STRING (SIZE(4)) -- DDDDDD.DD, BCD coded
}

MiscCallInfo ::= SEQUENCE {
    messageType [0] ENUMERATED {
        request(0),
        notification(1)
    }
}

MonitorMode ::= ENUMERATED {
    interrupted(0),
    notifyAndContinue(1),
    transparent(2)
}

Number ::= OCTET STRING (SIZE(2..16))

ReceivingSideID ::= CHOICE {
    receivingSideID [1] LegType
}

RedirectionInformation ::= OCTET STRING (SIZE (2))

RequestedInformationList ::= SEQUENCE SIZE(1..5) OF RequestedInformation

RequestedInformationTypeList ::= SEQUENCE SIZE(1..5) OF RequestedInformationType

RequestedInformation ::= SEQUENCE {
    requestedInformationType  [0] RequestedInformationType,
    requestedInformationValue [1] RequestedInformationValue
}

RequestedInformationType ::= ENUMERATED {
    callAttemptElapsedTime(0),
    callStopTime(1),
    callConnectedElapsedTime(2),
    calledAddress(3),
    releaseCause(30)
}

RequestedInformationValue ::= CHOICE {
    callAttemptElapsedTimeValue   [0] INTEGER (0..255),
    callStopTimeValue             [1] DateAndTime,
    callConnectedElapsedTimeValue [2] INTEGER (0..2147483647),
    calledAddressValue            [3] GenericNumber,
    releaseCause                  [30] Cause
}

RouteIndex ::= OCTET STRING (SIZE (1))

RouteList ::= SEQUENCE SIZE(1) OF RouteIndex

SCIBillingChargingCharacteristics ::= CHOICE {
    chargingInformation       [0] ChargingInformation,
    chargingAnalysisInputData [1] ChargingAnalysisInputData
}

ChargingInformation ::= SEQUENCE {
    orderStartOfCharging       [0] NULL OPTIONAL,
    chargeMessage              [1] ChargeMessage OPTIONAL,
    pulseBurst                 [2] INTEGER (1..255) OPTIONAL,
    createDefaultBillingRecord [3] NULL OPTIONAL
}

ChargeMessage ::= SEQUENCE {
    eventTypeCharging         [1] EventTypeCharging,
    eventSpecificInfoCharging [2] EventSpecificInfoCharging
}

SendingSideID ::= CHOICE {
    sendingSideID [0] LegType
}

ServiceKey ::= INTEGER (0..65535)

SFBillingChargingCharacteristics ::= SEQUENCE {
    tariffInformation        [0] TariffInformation OPTIONAL,
    tariffIndicator          [1] OCTET STRING (SIZE(2)) OPTIONAL,
    chargeNoChargeIndication [2] ChargeNoChargeIndication DEFAULT chargeableCall
}

ChargeNoChargeIndication ::= ENUMERATED {
    callFreeOfCharge (1),
    chargeableCall   (2)
}

SuspendTimer ::= INTEGER (0..120)

TariffInformation ::= SEQUENCE {
    numberOfStartPulses      [0] INTEGER (0..255),
    startInterval            [1] INTEGER (0..3276),
    startIntervalAccuracy    [2] StartIntervalAccuracy,
    numberOfPeriodicPulses   [3] INTEGER (0..255),
    periodicInterval         [4] INTEGER (0..3276),
    periodicIntervalAccuracy [5] PeriodicIntervalAccuracy,
    activationTime           [6] DateAndTime OPTIONAL
}

StartIntervalAccuracy ::= ENUMERATED {
    tenMilliSeconds        (1),
    oneHundredMilliSeconds (2),
    seconds                (3)
}

PeriodicIntervalAccuracy ::= ENUMERATED {
    tenMilliSeconds        (1),
    oneHundredMilliSeconds (2),
    seconds                (3)
}

TimerID ::= ENUMERATED {
    tssf(0) -- others for further study
}

TimerValue ::= INTEGER (0..2047)

END
