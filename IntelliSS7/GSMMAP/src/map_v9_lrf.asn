--------------------------------------------------------------------------------
--                                                                            --
--  Copyright 1999 -2002 IntelliNet Technologies, Inc. All Rights Reserved.   --
--              Manufactured in the United States of America.                 --
--        1990 W. New Haven Ste. 312, Melbourne, Florida, 32904 U.S.A.        --
--                                                                            --
--    This product and related documentation is protected by copyright and    --
--    distributed under licenses restricting its use, copying, distribution   --
--    and decompilation.  No part of this product or related documentation    --
--    may be reproduced in any form by any means without prior written        --
--    authorization of IntelliNet Technologies and its licensors, if any.     --
--                                                                            --
--    RESTRICTED RIGHTS LEGEND:  Use, duplication, or disclosure by the       --
--    government is subject to restrictions as set forth in subparagraph      --
--    (c)(1)(ii) of the Rights in Technical Data and Computer Software        --
--    clause at DFARS 252.227-7013 and FAR 52.227-19.                         --
--                                                                            --
--------------------------------------------------------------------------------
--                                                                            --
--  CONTRACT: INTERNAL                                                        --
--                                                                            --
--------------------------------------------------------------------------------
--
--  
--
--------------------------------------------------------------------------------

--------------------------------------------------------------------------------
--------------------------------------------------------------------------------
--
--  ASN.1 Module for GSM MAP 3G (MAP V9).
--
--  LRF (Local Reference Format) version (from specification).
--
--------------------------------------------------------------------------------
--------------------------------------------------------------------------------


--
--  Specification identification:
--  3GPP TS 29.002 V6.11.0 (2005-09)
--  3rd Generation Partnership Project;
--  Technical Specification Group Core Network and Terminals;
--  Mobile Application Part (MAP) specification;
--  (Release 6)
--

MAP-V9

DEFINITIONS

IMPLICIT TAGS

::=

BEGIN

--not used LocationUpdatingPackage-v3 ::= OPERATION-PACKAGE
    -- Supplier is HLR if Consumer is VLR
--not used  CONSUMER INVOKES {
--not used      updateLocation}
--not used  SUPPLIER INVOKES {
--not used      forwardCheckSs-Indication}
--not used 
--not used LocationCancellationPackage-v3 ::= OPERATION-PACKAGE
    -- Supplier is VLR or SGSN if Consumer is HLR
--not used  CONSUMER INVOKES {
--not used      cancelLocation}
--not used 
--not used RoamingNumberEnquiryPackage-v3 ::= OPERATION-PACKAGE
    -- Supplier is VLR if Consumer is HLR
--not used  CONSUMER INVOKES {
--not used      provideRoamingNumber}
--not used 
--not used InfoRetrievalPackage-v3 ::= OPERATION-PACKAGE
    -- Supplier is HLR if Consumer is VLR
    -- Supplier is HLR if Consumer is SGSN
--not used  CONSUMER INVOKES {
--not used      sendAuthenticationInfo}
--not used 
--not used InfoRetrievalPackage-v2 ::= OPERATION-PACKAGE
    -- Supplier is HLR if Consumer is VLR
    -- Supplier is HLR if Consumer is SGSN
--not used  CONSUMER INVOKES {
--not used      sendAuthenticationInfo}
--not used 
--not used InfoRetrievalPackage-v1 ::= OPERATION-PACKAGE
    -- Supplier is HLR or VLR if Consumer is VLR
    -- Supplier is HLR if Consumer is SGSN
--not used  CONSUMER INVOKES {
--not used      sendParameters}
--not used 
--not used InterVlrInfoRetrievalPackage-v3 ::= OPERATION-PACKAGE
    -- Supplier is VLR if Consumer is VLR
--not used  CONSUMER INVOKES {
--not used      sendIdentification}
--not used 
--not used InterVlrInfoRetrievalPackage-v2 ::= OPERATION-PACKAGE
    -- Supplier is VLR if Consumer is VLR
--not used  CONSUMER INVOKES {
--not used      sendIdentification}
--not used 
--not used IMSIRetrievalPackage-v2 ::= OPERATION-PACKAGE
    -- Supplier is HLR if Consumer is VLR
--not used  CONSUMER INVOKES {
--not used      sendIMSI}
--not used 
--not used CallControlTransferPackage-v4 ::= OPERATION-PACKAGE
    -- Supplier is GMSC if Consumer is VMSC
--not used  CONSUMER INVOKES {
--not used      resumeCallHandling}
--not used 
--not used SecureTransportHandlingPackage-v3 ::= OPERATION-PACKAGE
--not used  CONSUMER INVOKES {
--not used      SecureTransportClass1,  
                -- to be used if the original operation is a
                -- TCAP class 1 operation
--not used      SecureTransportClass2,  
                -- to be used if the original operation is a
                -- TCAP class 2 operation
--not used      SecureTransportClass3,  
                -- to be used if the original operation is a
                -- TCAP class 3 operation
--not used      SecureTransportClass4}  
                -- to be used if the original operation is a
                -- TCAP class 4 operation

--not used InterrogationPackage-v3 ::= OPERATION-PACKAGE
    -- Supplier is HLR or NPLR if Consumer is MSC
--not used  CONSUMER INVOKES {
--not used         sendRoutingInfo}
--not used 
--not used HandoverControlPackage-v3 ::= OPERATION-PACKAGE
    -- Supplier is MSCB if Consumer is MSCA
--not used     CONSUMER INVOKES {
--not used         prepareHandover,
--not used         forwardAccessSignalling}
--not used     SUPPLIER INVOKES {
--not used         sendEndSignal,
--not used         processAccessSignalling,
--not used         prepareSubsequentHandover}
--not used 
--not used HandoverControlPackage-v1 ::= OPERATION-PACKAGE
    -- Supplier is MSCB if Consumer is MSCA
--not used     CONSUMER INVOKES {
--not used         performHandover,
--not used         forwardAccessSignalling,
--not used         traceSubscriberActivity}
--not used     SUPPLIER INVOKES {
--not used         sendEndSignal,
--not used         noteInternalHandover,
--not used         processAccessSignalling,
--not used         performSubsequentHandover}
--not used 
--not used SubscriberDataMngtStandAlonePackage-v3 ::= OPERATION-PACKAGE
    -- Supplier is VLR or SGSN if Consumer is HLR
--not used     CONSUMER INVOKES {
--not used         insertSubscriberData,
--not used         deleteSubscriberData}
--not used 
--not used EquipmentMngtPackage-v2 ::= OPERATION-PACKAGE
    -- Supplier is EIR if Consumer is MSC
    -- Supplier is EIR if Consumer is SGSN
--not used     CONSUMER INVOKES {
--not used         checkIMEI}
--not used 
--not used SubscriberDataMngtPackage-v3 ::= OPERATION-PACKAGE
    -- Supplier is VLR or SGSN if Consumer is HLR
--not used     CONSUMER INVOKES {
--not used         insertSubscriberData}
--not used 
--not used ResetPackage-v2 ::= OPERATION-PACKAGE
    -- Supplier is VLR or SGSN if Consumer is HLR
--not used     CONSUMER INVOKES {
--not used         reset}
--not used 
--not used TracingStandAlonePackage-v3 ::= OPERATION-PACKAGE
    -- Supplier is VLR or SGSN if Consumer is HLR
--not used     CONSUMER INVOKES {
--not used         activateTraceMode,
--not used         deactivateTraceMode}
--not used 
--not used FunctionalSsPackage-v2 ::= OPERATION-PACKAGE
    -- Supplier is HLR if Consumer is VLR
--not used     CONSUMER INVOKES {
--not used         registerSS,
--not used         eraseSS,
--not used         activateSS,
--not used         deactivateSS,
--not used         registerPassword,
--not used         interrogateSS}
--not used     SUPPLIER INVOKES {
--not used         getPassword}
--not used 
--not used TracingPackage-v3 ::= OPERATION-PACKAGE
    -- Supplier is VLR or SGSN if Consumer is HLR
--not used     CONSUMER INVOKES {
--not used         activateTraceMode}
--not used 
--not used BindingPackage-v1 ::= OPERATION-PACKAGE
    -- Supplier is HLR if Consumer is VLR
    -- Supplier is gsmSCF if Consumer is HLR
--not used     CONSUMER INVOKES {
--not used         beginSubscriberActivity}
--not used 
--not used UnstructuredSsPackage-v2 ::= OPERATION-PACKAGE
    -- Supplier is HLR if Consumer is VLR
    -- Supplier is gsmSCF or HLR if Consumer is HLR
--not used     CONSUMER INVOKES {
--not used         processUnstructuredSS-Request}
--not used     SUPPLIER INVOKES {
--not used         unstructuredSS-Request,
--not used         unstructuredSS-Notify}
--not used 
--not used UnstructuredSsPackage-v1 ::= OPERATION-PACKAGE
    -- Supplier is HLR if Consumer is VLR
    -- Supplier is gsmSCF if Consumer is HLR
--not used     CONSUMER INVOKES {
--not used         processUnstructuredSS-Data}
--not used 
--not used MOShortMsgRelayPackage-v3 ::= OPERATION-PACKAGE
    -- Supplier is IWMSC if Consumer is MSC
    -- Supplier is IWMSC if Consumer is SGSN
--not used     CONSUMER INVOKES {
--not used         MO-forwardSM}
--not used 
--not used ShortMsgRelayPackage-v2 ::= OPERATION-PACKAGE
    -- Supplier is IWMSC if Consumer is MSC
    -- Supplier is MSC or SGSN if Consumer is GMSC
    -- Supplier is IWMSC if Consumer is SGSN
--not used     CONSUMER INVOKES {
--not used         forwardSM}
--not used 
--not used ShortMsgGatewayPackage-v3 ::= OPERATION-PACKAGE
    -- Supplier is HLR if Consumer is GMSC
--not used     CONSUMER INVOKES {
--not used         sendRoutingInfoForSM,
--not used         reportSM-DeliveryStatus}
--not used     SUPPLIER INVOKES {
--not used         informServiceCentre}
--not used 
--not used ShortMsgGatewayPackage-v1 ::= OPERATION-PACKAGE
    -- Supplier is HLR if Consumer is GMSC
--not used     CONSUMER INVOKES {
--not used         sendRoutingInfoForSM,
--not used         reportSMDeliveryStatus}
--not used 
--not used MTShortMsgRelayPackage-v3 ::= OPERATION-PACKAGE
    -- Supplier is MSC or SGSN if Consumer is GMSC
--not used     CONSUMER INVOKES {
--not used         MT-forwardSM}
--not used 
--not used MwdMngtPackage-v3 ::= OPERATION-PACKAGE
    -- Supplier is HLR if Consumer is SGSN
    -- Supplier is HLR if Consumer is VLR
--not used     CONSUMER INVOKES {
--not used         readyForSM}
--not used 
--not used MwdMngtPackage-v1 ::= OPERATION-PACKAGE
    -- Supplier is HLR if Consumer is VLR
--not used     CONSUMER INVOKES {
--not used         noteSubscriberPresent}
--not used 
--not used AlertingPackage-v2 ::= OPERATION-PACKAGE
    -- Supplier is IWMSC if Consumer is HLR
--not used     CONSUMER INVOKES {
--not used         alertServiceCentre}
--not used 
--not used AlertingPackage-v1 ::= OPERATION-PACKAGE
    -- Supplier is IWMSC if Consumer is HLR
--not used     CONSUMER INVOKES {
--not used         alertServiceCentreWithoutResult}
--not used 
--not used DataRestorationPackage-v3 ::= OPERATION-PACKAGE
    -- Supplier is HLR if Consumer is VLR
--not used     CONSUMER INVOKES {
--not used         restoreData}
--not used 
--not used PurgingPackage-v3 ::= OPERATION-PACKAGE
    -- Supplier is HLR if Consumer is VLR
    -- Supplier is HLR if Consumer is SGSN
--not used     CONSUMER INVOKES {
--not used         purgeMS}
--not used 
--not used SubscriberInformationEnquiryPackage-v3 ::= OPERATION-PACKAGE
    -- Supplier is VLR if Consumer is HLR
--not used     CONSUMER INVOKES {
--not used         provideSubscriberInfo}
--not used 
--not used AnyTimeInformationEnquiryPackage-v3 ::= OPERATION-PACKAGE
    -- Supplier is HLR or GMLC if Consumer is gsmSCF
--not used     CONSUMER INVOKES {
--not used         anyTimeInterrogation}
--not used 
--not used GroupCallControlPackage-v3 ::= OPERATION-PACKAGE
    -- Supplier is relay MSC if Consumer is anchor MSC
--not used     CONSUMER INVOKES {
--not used         prepareGroupCall,
--not used         forwardGroupCallSignalling}
--not used     SUPPLIER INVOKES {
--not used         sendGroupCallEndSignal,
--not used         processGroupCallSignalling}
--not used 
--not used ProvideSIWFSNumberPackage-v3 ::= OPERATION-PACKAGE
    -- Supplier is SIWF if Consumer is VMSC
--not used     CONSUMER INVOKES {
--not used         provideSIWFSNumber}
--not used 
--not used SIWFSSignallingModifyPackage-v3 ::= OPERATION-PACKAGE
    -- Supplier is SIWF if Consumer is VMSC
--not used     CONSUMER INVOKES {
--not used         sIWFSSignallingModify}
--not used 
--not used GprsLocationUpdatingPackage-v3 ::= OPERATION-PACKAGE
    -- Supplier is HLR if Consumer is SGSN
--not used     CONSUMER INVOKES {
--not used         updateGprsLocation}
--not used 
--not used GprsInterrogationPackage-v3 ::= OPERATION-PACKAGE
    -- Supplier is HLR if Consumer is GGSN
--not used     CONSUMER INVOKES {
--not used         sendRoutingInfoForGprs}
--not used 
--not used FailureReportingPackage-v3 ::= OPERATION-PACKAGE
    -- Supplier is HLR if Consumer is GGSN
--not used     CONSUMER INVOKES {
--not used         failureReport}
--not used 
--not used GprsNotifyingPackage-v3 ::= OPERATION-PACKAGE
    -- Supplier is GGSN if Consumer is HLR
--not used     CONSUMER INVOKES {
--not used         noteMsPresentForGprs}
--not used 
--not used SS-InvocationNotificationPackage-v3 ::= OPERATION-PACKAGE
    -- Supplier is gsmSCF if Consumer is MSC
    -- Supplier is gsmSCF if Consumer is HLR
--not used     CONSUMER INVOKES {
--not used         ss-InvocationNotification}
--not used 
--not used SetReportingStatePackage-v3 ::= OPERATION-PACKAGE
    -- Supplier is VLR if Consumer is HLR
--not used     CONSUMER INVOKES {
--not used         setReportingState}      
--not used 
--not used StatusReportPackage-v3 ::= OPERATION-PACKAGE
    -- Supplier is HLR if Consumer is VLR
--not used     CONSUMER INVOKES {
--not used         statusReport}      
--not used 
--not used RemoteUserFreePackage-v3 ::= OPERATION-PACKAGE
    -- Supplier is VLR if Consumer is HLR
--not used     CONSUMER INVOKES {
--not used         remoteUserFree}      
--not used 
--not used CallCompletionPackage-v3 ::= OPERATION-PACKAGE
    -- Supplier is HLR if Consumer is VLR
--not used     CONSUMER INVOKES {
--not used         registerCC-Entry,
--not used         eraseCC-Entry}
--not used 
--not used LocationSvcGatewayPackage-v3 ::= OPERATION-PACKAGE
    -- Supplier is HLR if Consumer is GMLC
--not used     CONSUMER INVOKES {
--not used         sendRoutingInfoForLCS}
--not used 
--not used LocationSvcEnquiryPackage-v3 ::= OPERATION-PACKAGE
    -- Supplier is MSC if Consumer is GMLC
--not used     CONSUMER INVOKES {
--not used         provideSubscriberLocation}
--not used     SUPPLIER INVOKES {
--not used         subscriberLocationReport}
--not used 
--not used IST-AlertingPackage-v3 ::= OPERATION-PACKAGE
    -- Supplier is HLR if Consumer is VMSC
    -- Supplier is HLR if Consumer is GMSC
--not used     CONSUMER INVOKES {
--not used         istAlert}
--not used 
--not used ServiceTerminationPackage-v3 ::= OPERATION-PACKAGE
    -- Supplier is VMSC or GMSC if Consumer is HLR
--not used     CONSUMER INVOKES {
--not used         istCommand}
--not used 
--not used MM-EventReportingPackage-v3 ::= OPERATION-PACKAGE
    -- Supplier is gsmSCF if Consumer is VLR
--not used     CONSUMER INVOKES {
--not used         noteMM-Event}
--not used 
--not used AnyTimeInformationHandlingPackage-v3 ::= OPERATION-PACKAGE
    -- Supplier is HLR if Consumer is gsmSCF
--not used     CONSUMER INVOKES {
--not used         anyTimeSubscriptionInterrogation,
--not used         anyTimeModification}
--not used 
--not used SubscriberDataModificationNotificationPackage-v3 ::= OPERATION-PACKAGE
    -- Supplier is gsmSCF if Consumer is HLR
--not used     CONSUMER INVOKES {
--not used         noteSubscriberDataModified}
--not used 
--not used AuthenticationFailureReportPackage-v3 ::= OPERATION-PACKAGE
    -- Supplier is HLR if Consumer is VLR
    -- Supplier is HLR if Consumer is SGSN
--not used     CONSUMER INVOKES {
--not used         authenticationFailureReport}
--not used 
--not used APPLICATION-CONTEXT MACRO ::=
--not used 
--not used BEGIN
--not used 
--not used TYPE NOTATION ::= Symmetric | InitiatorConsumerOf
--not used ResponderConsumerOf | empty
--not used 
--not used VALUE NOTATION ::= value(VALUE OBJECT IDENTIFIER)
--not used 
--not used Symmetric ::= "OPERATIONS OF" "{" PackageList "}"
--not used 
--not used InitiatorConsumerOf ::= "INITIATOR CONSUMER OF" "{" PackageList "}"
--not used 
--not used ResponderConsumerOf ::= "RESPONDER CONSUMER OF" "{" PackageList "}"
--not used         | empty
--not used 
--not used PackageList ::= Package | PackageList "," Package
--not used 
--not used Package ::= value(OPERATION-PACKAGE)
--not used         | type 
-- shall reference a package type
--not used 
--not used END
--not used 
--not used networkLocUpContext-v3 APPLICATION-CONTEXT
    -- Responder is HLR if Initiator is VLR
--not used     INITIATOR CONSUMER OF {
--not used         LocationUpdatingPackage-v3,
--not used         DataRestorationPackage-v3}
--not used     RESPONDER CONSUMER OF {
--not used         SubscriberDataMngtPackage-v3
--not used         TracingPackage-v3}
--not used ::= {map-ac networkLocUp(1) version3(3)}
--not used 
--not used locationCancellationContext-v3 APPLICATION-CONTEXT
    -- Responder is VLR or SGSN if Initiator is HLR
--not used     INITIATOR CONSUMER OF {
--not used         LocationCancellationPackage-v3}
--not used ::= {map-ac locationCancel(2) version3(3)}
--not used 
--not used roamingNumberEnquiryContext-v3 APPLICATION-CONTEXT
    -- Responder is VLR if Initiator is HLR
--not used     INITIATOR CONSUMER OF {
--not used         RoamingNumberEnquiryPackage-v3}
--not used ::= {map-ac roamingNbEnquiry(3) version3(3)}
--not used 
--not used locationInfoRetrievalContext-v3 APPLICATION-CONTEXT
    -- Responder is HLR or NPLR if Initiator is GMSC
--not used     INITIATOR CONSUMER OF {
--not used         InterrogationPackage-v3}
--not used ::= {map-ac locInfoRetrieval(5) version3(3)}
--not used 
--not used callControlTransferContext-v4 APPLICATION-CONTEXT
    -- Responder is GMSC if Initiator is VMSC
--not used     INITIATOR CONSUMER OF {
--not used         CallControlTransferPackage-v4}
--not used ::= {map-ac callControlTransfer(6) version4(4)}
--not used 
--not used SecureTransportHandlingContext-v3 APPLICATION-CONTEXT
--not used     INITIATOR CONSUMER OF {
--not used         SecureTransportHandlingPackage-v3}
--not used ::= {map-ac secureTransportHandling(40) version3(3)}
--not used 
--not used resetContext-v2 APPLICATION-CONTEXT
    -- Responder is VLR or SGSN if Initiator is HLR
--not used     INITIATOR CONSUMER OF {
--not used         ResetPackage-v2}
--not used ::= {map-ac reset(10) version2(2)}
--not used 
--not used handoverControlContext-v3 APPLICATION-CONTEXT
    -- Responder is MSCB if Initiator is MSCA
--not used     INITIATOR CONSUMER OF {
--not used         HandoverControlPackage-v3}
--not used ::= {map-ac handoverControl(11) version3(3)}
--not used 
--not used imsiRetrievalContext-v2 APPLICATION-CONTEXT
    -- Responder is HLR if Initiator is VLR
--not used     INITIATOR CONSUMER OF {
--not used         IMSIRetrievalPackage-v2}
--not used ::= {map-ac imsiRetrieval(26) version2(2)}
--not used 
--not used equipmentMngtContext-v2 APPLICATION-CONTEXT
    -- Responder is EIR if Initiator is MSC
    -- Responder is EIR if Initiator is SGSN
--not used     INITIATOR CONSUMER OF {
--not used         EquipmentMngtPackage-v2}
--not used ::= {map-ac equipmentMngt(13) version2(2)}
--not used 
--not used infoRetrievalContext-v3 APPLICATION-CONTEXT
    -- Responder is HLR if Initiator is VLR
    -- Responder is HLR if Initiator is SGSN
--not used     INITIATOR CONSUMER OF {
--not used         InfoRetrievalPackage-v3}
--not used ::= {map-ac infoRetrieval(14) version3(3)}
--not used 
--not used infoRetrievalContext-v2 APPLICATION-CONTEXT
    -- Responder is HLR if Initiator is VLR
    -- Responder is HLR if Initiator is SGSN
--not used     INITIATOR CONSUMER OF {
--not used         InfoRetrievalPackage-v2}
--not used ::= {map-ac infoRetrieval(14) version2(2)}
--not used 
--not used interVlrInfoRetrievalContext-v3 APPLICATION-CONTEXT
    -- Responder is VLR if Initiator is VLR
--not used     INITIATOR CONSUMER OF {
--not used         InterVlrInfoRetrievalPackage-v3}
--not used ::= {map-ac interVlrInfoRetrieval(15) version3(3)}
--not used 
--not used interVlrInfoRetrievalContext-v2 APPLICATION-CONTEXT
    -- Responder is VLR if Initiator is VLR
--not used     INITIATOR CONSUMER OF {
--not used         InterVlrInfoRetrievalPackage-v2}
--not used ::= {map-ac interVlrInfoRetrieval(15) version2(2)}
--not used 
--not used subscriberDataMngtContext-v3 APPLICATION-CONTEXT
    -- Responder is VLR or SGSN if Initiator is HLR
--not used     INITIATOR CONSUMER OF {
--not used         SubscriberDataMngtStandAlonePackage-v3}
--not used ::= {map-ac subscriberDataMngt(16) version3(3)}
--not used 
--not used tracingContext-v3 APPLICATION-CONTEXT
    -- Responder is VLR or SGSN if Initiator is HLR
--not used     INITIATOR CONSUMER OF {
--not used         TracingStandAlonePackage-v3}
--not used ::= {map-ac tracing(17) version3(3)}
--not used 
--not used networkFunctionalSsContext-v2 APPLICATION-CONTEXT
    -- Responder is HLR, Initiator is VLR
--not used     INITIATOR CONSUMER OF {
--not used         FunctionalSsPackage-v2}
--not used ::= {map-ac networkFunctionalSs(18) version2(2)}
--not used 
--not used networkFunctionalSsContext-v1 APPLICATION-CONTEXT
    -- Responder is HLR, Initiator is VLR
--not used     INITIATOR CONSUMER OF {
--not used         FunctionalSsPackage-v1,
--not used         UnstructuredSsPackage-v1,
--not used         BindingPackage-v1}
--not used ::= {map-ac networkFunctionalSs(18) version1(1)}
--not used 
--not used networkUnstructuredSsContext-v2 APPLICATION-CONTEXT
    -- Responder is HLR, Initiator is VLR
    -- Responder is VLR, Initiator is HLR
    -- Responder is gsmSCF, Initiator is HLR
    -- Responder is HLR, Initiator is gsmSCF
    -- Responder is HLR, Initiator is HLR
--not used     OPERATIONS OF {
--not used         UnstructuredSsPackage-v2}
--not used ::= {map-ac networkUnstructuredSs(19) version2(2)}
--not used 
--not used shortMsgGatewayContext-v3 APPLICATION-CONTEXT
    -- Responder is HLR if Initiator is GMSC
--not used     INITIATOR CONSUMER OF {
--not used         ShortMsgGatewayPackage-v3}
--not used ::= {map-ac shortMsgGateway(20) version3(3)}
--not used 
--not used shortMsgMO-RelayContext-v3 APPLICATION-CONTEXT
    -- Responder is IWMSC if Initiator is MSC
    -- Responder is IWMSC if Initiator is SGSN
--not used     INITIATOR CONSUMER OF {
--not used         MOShortMsgRelayPackage-v3}
--not used ::= {map-ac shortMsgMO-Relay(21) version3(3)}
--not used 
--not used shortMsgAlertContext-v2 APPLICATION-CONTEXT
    -- Responder is IWMSC if Initiator is HLR
--not used     INITIATOR CONSUMER OF {
--not used         AlertingPackage-v2}
--not used ::= {map-ac shortMsgAlert(23) version2(2)}
--not used 
--not used mwdMngtContext-v3 APPLICATION-CONTEXT
    -- Responder is HLR if Initiator is SGSN
    -- Responder is HLR if Initiator is VLR
--not used     INITIATOR CONSUMER OF {
--not used         MwdMngtPackage-v3}
--not used ::= {map-ac mwdMngt(24) version3(3)}
--not used 
--not used shortMsgMT-RelayContext-v3 APPLICATION-CONTEXT
    -- Responder is MSC or SGSN if Initiator is GMSC
--not used     INITIATOR CONSUMER OF {
--not used         MTShortMsgRelayPackage-v3}
--not used ::= {map-ac shortMsgMT-Relay(25) version3(3)}
--not used 
--not used msPurgingContext-v3 APPLICATION-CONTEXT
    -- Responder is HLR if Initiator is VLR
    -- Responder is HLR if Initiator is SGSN
--not used     INITIATOR CONSUMER OF {
--not used         purgingPackage-v3}
--not used ::= {map-ac msPurging(27) version3(3)}
--not used 
--not used subscriberInfoEnquiryContext-v3 APPLICATION-CONTEXT
    -- Responder is VLR if Initiator is HLR
--not used     INITIATOR CONSUMER OF {
--not used         SubscriberInformationEnquiryPackage-v3}
--not used ::= {map-ac subscriberInfoEnquiry(28) version3(3)}
--not used 
--not used anyTimeInfoEnquiryContext-v3 APPLICATION-CONTEXT
    -- Responder is HLR or GMLC if Initiator is gsmSCF
--not used     INITIATOR CONSUMER OF {
--not used         AnyTimeInformationEnquiryPackage-v3}
--not used ::= {map-ac anyTimeInfoEnquiry(29) version3(3)}
--not used 
--not used groupCallControlContext-v3 APPLICATION-CONTEXT
    -- Responder is relay MSC if Initiator is anchor MSC
--not used     INITIATOR CONSUMER OF {
--not used         GroupCallControlPackage-v3}
--not used ::= {map-ac groupCallControl(31) version3(3)}
--not used 
--not used sIWFSAllocationContext-v3 APPLICATION-CONTEXT
    -- Responder is SIWF if Initiater is VMSC
--not used     INITIATOR CONSUMER OF {
--not used         ProvideSIWFSNumberPackage-v3,
--not used         SIWFSSignallingModifyPackage-v3}
--not used ::= {map-ac sIWFSAllocation (12) version3(3)}
--not used 
--not used gprsLocationUpdateContext-v3 APPLICATION-CONTEXT
    -- Responder is HLR if Initiator is SGSN
--not used     INITIATOR CONSUMER OF {
--not used         GprsLocationUpdatingPackage-v3}
--not used     RESPONDER CONSUMER OF {
--not used         SubscriberDataMngtPackage-v3
--not used         TracingPackage-v3}
--not used ::= {map-ac gprsLocationUpdate(32) version3(3)}
--not used 
--not used gprsLocationInfoRetrievalContext-v3 APPLICATION-CONTEXT
    -- Responder is HLR if Initiator is GGSN
--not used     INITIATOR CONSUMER OF {
--not used         GprsInterrogationPackage-v3}
--not used ::= {map-ac gprsLocationInfoRetrieval(33) version3(3)}
--not used 
--not used failureReportContext-v3 APPLICATION-CONTEXT
    -- Responder is HLR if Initiator is GGSN
--not used     INITIATOR CONSUMER OF {
--not used         FailureReportingPackage-v3}
--not used ::= {map-ac failureReport(34) version3(3)}
--not used 
--not used gprsNotifyContext-v3 APPLICATION-CONTEXT
    -- Responder is GGSN if Initiator is HLR
--not used     INITIATOR CONSUMER OF {
--not used         GprsNotifyingPackage-v3}
--not used ::= {map-ac gprsNotify(35) version3(3)}
--not used 
--not used ss-InvocationNotificationContext-v3 APPLICATION-CONTEXT
    -- Responder is gsmSCF, Initiator is MSC
    -- Responder is gsmSCF, Initiator is HLR
--not used     INITIATOR CONSUMER OF {
--not used         SS-InvocationNotificationPackage-v3} 
--not used ::= {map-ac ss-InvocationNotification(36) version3(3)}
--not used 
--not used reportingContext-v3 APPLICATION-CONTEXT
    -- Responder is VLR if Initiator is HLR
    -- Responder is HLR if Initiator is VLR
--not used     INITIATOR CONSUMER OF {
--not used         SetReportingStatePackage-v3,
--not used         StatusReportPackage-v3,
--not used         RemoteUserFreePackage-v3}
--not used     RESPONDER CONSUMER OF {
--not used         SetReportingStatePackage-v3,
--not used         StatusReportPackage-v3}
--not used ::= {map-ac reporting(7) version3(3)}
--not used 
--not used callCompletionContext-v3 APPLICATION-CONTEXT
    -- Responder is HLR if Initiator is VLR
--not used     INITIATOR CONSUMER OF {
--not used         CallCompletionPackage-v3}
--not used ::= {map-ac callCompletion(8) version3(3)}
--not used 
--not used locationSvcGatewayContext-v3 APPLICATION-CONTEXT
    -- Responder is HLR if Initiator is GMLC
--not used     INITIATOR CONSUMER OF {
--not used         locationSvcGatewayPackage-v3}
--not used ::= {map-ac locationSvcGateway(37) version3(3)}
--not used 
--not used locationSvcEnquiryContext-v3 APPLICATION-CONTEXT
    -- Responder is MSC if Initiator is GMLC
--not used     INITIATOR CONSUMER OF {
--not used         locationSvcEnquiryPackage-v3}
--not used ::= {map-ac locationScvEnquiry(38) version3 (3)}
--not used 
--not used istAlertingContext-v3 APPLICATION-CONTEXT
    -- Responder is HLR if Initiator is VMSC
    -- Responder is HLR if Initiator is GMSC
--not used     INITIATOR CONSUMER OF {
--not used         IST-AlertingPackage-v3}
--not used ::= {map-ac alerting(4) version3(3)}
--not used 
--not used serviceTerminationContext-v3 APPLICATION-CONTEXT
    -- Responder is VMSC or GMSC if Initiator is HLR
--not used     INITIATOR CONSUMER OF {
--not used         ServiceTerminationPackage-v3}
--not used ::= {map-ac serviceTermination(9) version3(3)}
--not used 
--not used mm-EventReportingContext-v3 APPLICATION-CONTEXT
    -- Responder is gsmSCF, Initiator is VLR
--not used     INITIATOR CONSUMER OF {
--not used         MM-EventReportingPackage-v3} 
--not used ::= {map-ac mm-EventReporting(42) version3(3)}
--not used 
--not used anyTimeInfohandlingContext-v3 APPLICATION-CONTEXT
    -- Responder is HLR if Initiator is gsmSCF
--not used     INITIATOR CONSUMER OF {
--not used         AnyTimeInformationHandlingPackage-v3}
--not used ::= {map-ac anyTimeInfoHandling(43) version3(3)}
--not used 
--not used subscriberDataModificationNotificationContext-v3 APPLICATION-CONTEXT
    -- Responder is gsmSCF, Initiator is HLR
--not used     INITIATOR CONSUMER OF {
--not used         SubscriberDataModificationNotificationPackage-v3} 
--not used ::= {map-ac subscriberDataModificationNotification(22) version3(3)}
--not used 
--not used authenticationFailureReportContext-v3 APPLICATION-CONTEXT
    -- Responder is HLR if Initiator is VLR
    -- Responder is HLR if Initiator is SGSN
--not used     INITIATOR CONSUMER OF {
--not used         AuthenticationFailureReportPackage-v3 }
--not used ::= {map-ac failureReport(39) version3(3)}
--not used 

-- Module ----------------------------------------------------------------------
--------------------------------------------------------------------------------
-- MAP ASN.1 Module for application-context-names
--------------------------------------------------------------------------------
--------------------------------------------------------------------------------

--not used MAP-ApplicationContexts {
--not used    ccitt identified-organization (4) etsi (0) mobileDomain (0)
--not used    gsm-Network (1) modules (3) map-ApplicationContexts (2) version8 (8)}
--not used 
--not used DEFINITIONS
--not used 
--not used ::=
--not used 
--not used BEGIN
--not used 
--not used 
-- EXPORTS everything
--not used 
--not used 
--not used IMPORTS
--not used     gsm-NetworkId,
--not used     ac-Id
--not used FROM MobileDomainDefinitions {
--not used    ccitt (0) identified-organization (4) etsi (0) mobileDomain (0)
--not used    mobileDomainDefinitions (0) version1 (1)}
--not used ;
--not used 
-- application-context-names
--not used 
--not used map-ac  OBJECT IDENTIFIER ::= {gsm-NetworkId ac-Id}
--not used 
--not used networkLocUpContext-v3  OBJECT IDENTIFIER ::=
--not used     {map-ac networkLocUp(1) version3(3)}
--not used 
--not used locationCancellationContext-v3  OBJECT IDENTIFIER ::=
--not used     {map-ac locationCancel(2) version3(3)}
--not used 
--not used roamingNumberEnquiryContext-v3  OBJECT IDENTIFIER ::=
--not used     {map-ac roamingNbEnquiry(3) version3(3)}
--not used 
--not used authenticationFailureReportContext-v3  OBJECT IDENTIFIER ::=
--not used     {map-ac authenticationFailureReport(39) version3(3)}
--not used 
--not used locationInfoRetrievalContext-v3  OBJECT IDENTIFIER ::=
--not used     {map-ac locInfoRetrieval(5) version3(3)}
--not used 
--not used resetContext-v2  OBJECT IDENTIFIER ::=
--not used     {map-ac reset(10) version2(2)}
--not used 
--not used handoverControlContext-v3  OBJECT IDENTIFIER ::=
--not used     {map-ac handoverControl(11) version3(3)}
--not used 
--not used equipmentMngtContext-v2  OBJECT IDENTIFIER ::=
--not used     {map-ac equipmentMngt(13) version2(2)}
--not used 
--not used infoRetrievalContext-v3  OBJECT IDENTIFIER ::=
--not used     {map-ac infoRetrieval(14) version3(3)}
--not used 
--not used interVlrInfoRetrievalContext-v3  OBJECT IDENTIFIER ::=
--not used     {map-ac interVlrInfoRetrieval(15) version3(3)}
--not used 
--not used subscriberDataMngtContext-v3  OBJECT IDENTIFIER ::=
--not used     {map-ac subscriberDataMngt(16) version3(3)}
--not used 
--not used tracingContext-v3  OBJECT IDENTIFIER ::=
--not used     {map-ac tracing(17) version3(3)}
--not used 
--not used networkFunctionalSsContext-v2  OBJECT IDENTIFIER ::=
--not used     {map-ac networkFunctionalSs(18) version2(2)}
--not used 
--not used networkUnstructuredSsContext-v2  OBJECT IDENTIFIER ::=
--not used     {map-ac networkUnstructuredSs(19) version2(2)}
--not used 
--not used shortMsgGatewayContext-v3  OBJECT IDENTIFIER ::=
--not used     {map-ac shortMsgGateway(20) version3(3)}
--not used 
--not used shortMsgMO-RelayContext-v3  OBJECT IDENTIFIER ::=
--not used     {map-ac shortMsgMO-Relay(21) version3(3)}
--not used 
--not used shortMsgAlertContext-v2  OBJECT IDENTIFIER ::=
--not used     {map-ac shortMsgAlert(23) version2(2)}
--not used 
--not used mwdMngtContext-v3  OBJECT IDENTIFIER ::=
--not used     {map-ac mwdMngt(24) version3(3)}
--not used 
--not used shortMsgMT-RelayContext-v3  OBJECT IDENTIFIER ::=
--not used     {map-ac shortMsgMT-Relay(25) version3(3)}
--not used 
--not used imsiRetrievalContext-v2  OBJECT IDENTIFIER ::=
--not used     {map-ac imsiRetrieval(26) version2(2)}
--not used 
--not used msPurgingContext-v3  OBJECT IDENTIFIER ::=
--not used     {map-ac msPurging(27) version3(3)}
--not used 
--not used subscriberInfoEnquiryContext-v3  OBJECT IDENTIFIER ::=
--not used     {map-ac subscriberInfoEnquiry(28) version3(3)}
--not used 
--not used anyTimeInfoEnquiryContext-v3  OBJECT IDENTIFIER ::=
--not used     {map-ac anyTimeInfoEnquiry(29) version3(3)}
--not used 
--not used callControlTransferContext-v4  OBJECT IDENTIFIER ::=
--not used     {map-ac callControlTransfer(6) version4(4)}
--not used 
--not used ss-InvocationNotificationContext-v3  OBJECT IDENTIFIER ::=
--not used     {map-ac ss-InvocationNotification(36) version3(3)}
--not used 
--not used sIWFSAllocationContext-v3  OBJECT IDENTIFIER ::=
--not used     {map-ac sIWFSAllocation(12) version3(3)}
--not used 
--not used groupCallControlContext-v3  OBJECT IDENTIFIER ::=
--not used     {map-ac groupCallControl(31) version3(3)}
--not used 
--not used gprsLocationUpdateContext-v3  OBJECT IDENTIFIER ::=
--not used     {map-ac gprsLocationUpdate(32) version3(3)}
--not used 
--not used gprsLocationInfoRetrievalContext-v3  OBJECT IDENTIFIER ::=
--not used     {map-ac gprsLocationInfoRetrieval(33) version3(3)}
--not used 
--not used failureReportContext-v3  OBJECT IDENTIFIER ::=
--not used     {map-ac failureReport(34) version3(3)}
--not used 
--not used gprsNotifyContext-v3  OBJECT IDENTIFIER ::=
--not used     {map-ac gprsNotify(35) version3(3)}
--not used 
--not used reportingContext-v3  OBJECT IDENTIFIER ::=
--not used     {map-ac reporting(7) version3(3)}
--not used 
--not used callCompletionContext-v3  OBJECT IDENTIFIER ::=
--not used     {map-ac callCompletion(8) version3(3)}
--not used 
--not used istAlertingContext-v3  OBJECT IDENTIFIER ::=
--not used     {map-ac istAlerting(4) version3(3)}
--not used 
--not used serviceTerminationContext-v3  OBJECT IDENTIFIER ::=
--not used     {map-ac immediateTermination(9) version3(3)}
--not used 
--not used locationSvcGatewayContext-v3  OBJECT IDENTIFIER ::=
--not used     {map-ac locationSvcGateway(37) version3(3)}
--not used 
--not used locationSvcEnquiryContext-v3  OBJECT IDENTIFIER ::=
--not used     {map-ac locationSvcEnquiry(38) version3(3)}
--not used 
--not used 
--not used mm-EventReportingContext-v3  OBJECT IDENTIFIER ::=
--not used     {map-ac mm-EventReporting(42) version3(3)}
--not used 
--not used anyTimeInfoHandlingContext-v3  OBJECT IDENTIFIER ::=
--not used     {map-ac anyTimeInfoHandling(43) version3(3)}
--not used 
--not used subscriberDataModificationNotificationContext-v3  OBJECT IDENTIFIER ::=
--not used     {map-ac subscriberDataModificationNotification(22) version3(3)}
--not used 
--not used secureTransportHandlingContext-v3  OBJECT IDENTIFIER ::=
--not used     {map-ac secureTransportHandling(40) version3(3)}

-- The following Object Identifiers are reserved for application-
-- contexts existing in previous versions of the protocol

-- AC Name & Version    Object Identifier
-- 
-- networkLocUpContext-v1   map-ac networkLocUp (1) version1 (1)
-- networkLocUpContext-v2   map-ac networkLocUp (1) version2 (2)
-- locationCancellationContext-v1   map-ac locationCancellation (2) version1 (1)
-- locationCancellationContext-v2   map-ac locationCancellation (2) version2 (2)
-- roamingNumberEnquiryContext-v1   map-ac roamingNumberEnquiry (3) version1 (1)
-- roamingNumberEnquiryContext-v2   map-ac roamingNumberEnquiry (3) version2 (2)
-- locationInfoRetrievalContext-v1  map-ac locationInfoRetrieval (5)    version1 (1)
-- locationInfoRetrievalContext-v2  map-ac locationInfoRetrieval (5)    version2 (2)
-- resetContext-v1  map-ac reset (10)   version1 (1)
-- handoverControlContext-v1    map-ac handoverControl (11) version1 (1)
-- handoverControlContext-v2    map-ac handoverControl (11) version2 (2)
-- equipmentMngtContext-v1  map-ac equipmentMngt (13)   version1 (1)
-- infoRetrievalContext-v1  map-ac infoRetrieval (14)   version1 (1) 
-- infoRetrievalContext-v2  map-ac infoRetrieval (14)   version2 (2)
-- interVlrInfoRetrievalContext-v2  map-ac interVlrInfoRetrieval (15)   version2 (2)
-- subscriberDataMngtContext-v1 map-ac subscriberDataMngt (16)  version1 (1)
-- subscriberDataMngtContext-v2 map-ac subscriberDataMngt (16)  version2 (2)
-- tracingContext-v1    map-ac tracing (17) version1 (1)
-- tracingContext-v2    map-ac tracing (17) version2 (2)
-- networkFunctionalSsContext-v1    map-ac networkFunctionalSs (18) version1 (1)
-- shortMsgGatewayContext-v1    map-ac shortMsgGateway (20) version1 (1)
-- shortMsgGatewayContext-v2    map-ac shortMsgGateway (20) version2 (2)
-- shortMsgRelayContext-v1  map-ac shortMsgRelay (21)   version1 (1)
-- shortMsgAlertContext-v1  map-ac shortMsgAlert (23)   version1 (1)
-- mwdMngtContext-v1    map-ac mwdMngt (24) version1 (1)
-- mwdMngtContext-v2    map-ac mwdMngt (24) version2 (2)
-- shortMsgMT-RelayContext-v2   map-ac shortMsgMT-Relay (25)    version2 (2)
-- msPurgingContext-v2  map-ac msPurging (27)   version2 (2) 
-- callControlTransferContext-v3    map-ac callControlTransferContext (6)   version3 (3)

--not used 
--not used END
--not used 
--------------------------------------------------------------------------------
--------------------------------------------------------------------------------
--------------------------------------------------------------------------------


-- Module ----------------------------------------------------------------------
--------------------------------------------------------------------------------
-- MAP Dialogue Information.
--------------------------------------------------------------------------------
--------------------------------------------------------------------------------

--not used MAP-DialogueInformation {
--not used    ccitt identified-organization (4) etsi (0) mobileDomain (0)
--not used    gsm-Network (1) modules (3) map-DialogueInformation (3) version8 (8)}
--not used 
--not used DEFINITIONS
--not used 
--not used IMPLICIT TAGS
--not used 
--not used ::=
--not used 
--not used BEGIN
--not used 
--not used EXPORTS
--not used     map-DialogueAS,
--not used     MAP-DialoguePDU,
--not used     map-ProtectedDialogueAS,
--not used     MAP-ProtectedDialoguePDU
--not used 
--not used ;
--not used 
--not used IMPORTS
--not used     gsm-NetworkId,
--not used     as-Id
--not used FROM MobileDomainDefinitions {
--not used    ccitt (0) identified-organization (4) etsi (0) mobileDomain (0)
--not used    mobileDomainDefinitions (0) version1 (1)}
--not used 
--not used     AddressString
--not used FROM MAP-CommonDataTypes {
--not used    ccitt identified-organization (4) etsi (0) mobileDomain (0)
--not used    gsm-Network(1) modules (3) map-CommonDataTypes (18) version8 (8)}
--not used 
--not used     ExtensionContainer
--not used FROM MAP-ExtensionDataTypes {
--not used    ccitt identified-organization (4) etsi (0) mobileDomain (0)
--not used    gsm-Network (1) modules (3) map-ExtensionDataTypes (21) version8 (8)}
--not used 
--not used     SecurityHeader,
--not used     ProtectedPayload
--not used FROM MAP-ST-DataTypes {
--not used    ccitt identified-organization (4) etsi (0) mobileDomain (0)
--not used    gsm-Network (1) modules (3) map-ST-DataTypes (27) version8 (8)}
--not used 
--not used ;
--not used 
--not used 
-- abstract syntax name for MAP-DialoguePDU
--not used 
--not used map-DialogueAS  OBJECT IDENTIFIER ::=
--not used     {gsm-NetworkId as-Id map-DialoguePDU (1) version1 (1)}

MAP-DialoguePDU ::= CHOICE {
    map-open        [0] MAP-OpenInfo,
    map-accept      [1] MAP-AcceptInfo,
    map-close       [2] MAP-CloseInfo,
    map-refuse      [3] MAP-RefuseInfo,
    map-userAbort   [4] MAP-UserAbortInfo,
    map-providerAbort   [5] MAP-ProviderAbortInfo}

MAP-OpenInfo ::= SEQUENCE {
    destinationReference    [0] AddressString   OPTIONAL,
    originationReference    [1] AddressString   OPTIONAL,
    ...,
    extensionContainer  ExtensionContainer  OPTIONAL
    -- extensionContainer must not be used in version 2
    }

MAP-AcceptInfo ::= SEQUENCE {
    ...,
    extensionContainer  ExtensionContainer  OPTIONAL
    -- extensionContainer must not be used in version 2
    }

MAP-CloseInfo ::= SEQUENCE {
    ...,
    extensionContainer  ExtensionContainer  OPTIONAL
    -- extensionContainer must not be used in version 2
    }

MAP-RefuseInfo ::= SEQUENCE {
    reason  Reason,
    ...,
    extensionContainer  ExtensionContainer  OPTIONAL,
    -- extensionContainer must not be used in version 2
    alternativeApplicationContext   OBJECT IDENTIFIER   OPTIONAL
    -- alternativeApplicationContext must not be used in version 2
    }

Reason ::= ENUMERATED {
    noReasonGiven   (0),
    invalidDestinationReference (1),
    invalidOriginatingReference (2),
    encapsulatedAC-NotSupported (3) ,
    transportProtectionNotAdequate  (4)}
    -- encapsulatedAC-NotSupported and transportProtectionNotAdequate must not be used in 
    -- dialogues with an AC different from secureTransportHandling

MAP-UserAbortInfo ::= SEQUENCE {
    map-UserAbortChoice MAP-UserAbortChoice,
    ...,
    extensionContainer  ExtensionContainer  OPTIONAL
    -- extensionContainer must not be used in version 2
    }

MAP-UserAbortChoice ::= CHOICE {
    userSpecificReason  [0] NULL,
    userResourceLimitation  [1] NULL,
    resourceUnavailable [2] ResourceUnavailableReason,
    applicationProcedureCancellation    [3] ProcedureCancellationReason}

ResourceUnavailableReason ::= ENUMERATED {
    shortTermResourceLimitation  (0),
    longTermResourceLimitation  (1)}

ProcedureCancellationReason ::= ENUMERATED {
    handoverCancellation  (0),
    radioChannelRelease  (1),
    networkPathRelease  (2),
    callRelease  (3),
    associatedProcedureFailure  (4),
    tandemDialogueRelease  (5),
    remoteOperationsFailure  (6)}

MAP-ProviderAbortInfo ::= SEQUENCE {
    map-ProviderAbortReason MAP-ProviderAbortReason,
    ...,
    extensionContainer  ExtensionContainer  OPTIONAL
    -- extensionContainer must not be used in version 2
    }

MAP-ProviderAbortReason ::= ENUMERATED {
    abnormalDialogue  (0),
    invalidPDU  (1)}

-- abstract syntax name for MAP-ProtectedDialoguePDU

--not used map-ProtectedDialogueAS  OBJECT IDENTIFIER ::=
--not used     {gsm-NetworkId as-Id map-ProtectedDialoguePDU (3) version1 (1)}

MAP-ProtectedDialoguePDU ::= SEQUENCE {
    encapsulatedAC  OBJECT IDENTIFIER,
    securityHeader  SecurityHeader  OPTIONAL,
    protectedPayload    ProtectedPayload    OPTIONAL,
    ...}
    -- The protectedPayload carries the result of applying the security function 
    -- defined in 3G TS 33.102 to the encoding of the securely transported 
    -- MAP-DialoguePDU


------------------------------------------------------------
-- Added type Map-UserInfo.
------------------------------------------------------------

MAP-UserInfo ::= SEQUENCE OF EXTERNAL


--not used 
--not used END
--not used 

--------------------------------------------------------------------------------
--------------------------------------------------------------------------------
--------------------------------------------------------------------------------


-- Module ----------------------------------------------------------------------
--------------------------------------------------------------------------------
-- MAP Protocol.
--------------------------------------------------------------------------------
--------------------------------------------------------------------------------
 
--not impl MAP-Protocol {
--not impl    ccitt identified-organization (4) etsi (0) mobileDomain (0)
--not impl    gsm-Network (1) modules (3) map-Protocol (4) version8 (8)}
--not impl 
--not impl DEFINITIONS
--not impl 
--not impl ::=
--not impl 
--not impl BEGIN
--not impl 
--not impl IMPORTS
--not impl     UpdateLocation,
--not impl     CancelLocation,
--not impl     PurgeMS,
--not impl     SendIdentification,
--not impl     UpdateGprsLocation,
--not impl     PrepareHandover,
--not impl     SendEndSignal,
--not impl     ProcessAccessSignalling,
--not impl     ForwardAccessSignalling,
--not impl     PrepareSubsequentHandover,
--not impl     SendAuthenticationInfo,
--not impl AuthenticationFailureReport,
--not impl     CheckIMEI,
--not impl     InsertSubscriberData,
--not impl     DeleteSubscriberData,
--not impl     Reset,
--not impl     ForwardCheckSS-Indication,
--not impl     RestoreData,
--not impl     ProvideSubscriberInfo,
--not impl     AnyTimeInterrogation,
--not impl     AnyTimeSubscriptionInterrogation,
--not impl     AnyTimeModification,
--not impl     SendRoutingInfoForGprs,
--not impl     FailureReport,
--not impl     NoteMsPresentForGprs,
--not impl     NoteMM-Event,
--not impl     NoteSubscriberDataModified
--not impl 
--not impl 
--not impl FROM MAP-MobileServiceOperations {
--not impl    ccitt identified-organization (4) etsi (0) mobileDomain (0)
--not impl    gsm-Network (1) modules (3) map-MobileServiceOperations (5)
--not impl    version8 (8)}
--not impl 
--not impl     ActivateTraceMode,
--not impl     DeactivateTraceMode,
--not impl     SendIMSI
--not impl FROM MAP-OperationAndMaintenanceOperations {
--not impl    ccitt identified-organization (4) etsi (0) mobileDomain (0)
--not impl    gsm-Network (1) modules (3) map-OperationAndMaintenanceOperations (6)
--not impl    version8 (8)}
--not impl 
--not impl     SendRoutingInfo,
--not impl     ProvideRoamingNumber,
--not impl     ResumeCallHandling,
--not impl     ProvideSIWFSNumber,
--not impl     SIWFSSignallingModify,
--not impl     SetReportingState,
--not impl     StatusReport,
--not impl     RemoteUserFree,
--not impl     IST-Alert,
--not impl     IST-Command
--not impl FROM MAP-CallHandlingOperations {
--not impl    ccitt identified-organization (4) etsi (0) mobileDomain (0)
--not impl    gsm-Network (1) modules (3) map-CallHandlingOperations (7)
--not impl    version8 (8)}
--not impl 
--not impl     RegisterSS,
--not impl     EraseSS,
--not impl     ActivateSS,
--not impl     DeactivateSS,
--not impl     InterrogateSS,
--not impl     ProcessUnstructuredSS-Request,
--not impl     UnstructuredSS-Request,
--not impl     UnstructuredSS-Notify,
--not impl     RegisterPassword,
--not impl     GetPassword,
--not impl     SS-InvocationNotification,
--not impl     RegisterCC-Entry,
--not impl     EraseCC-Entry
--not impl FROM MAP-SupplementaryServiceOperations {
--not impl    ccitt identified-organization (4) etsi (0) mobileDomain (0)
--not impl    gsm-Network (1) modules (3) map-SupplementaryServiceOperations (8)
--not impl    version8 (8)}
--not impl 
--not impl     SendRoutingInfoForSM,
--not impl     MO-ForwardSM,
--not impl     MT-ForwardSM,
--not impl     ReportSM-DeliveryStatus,
--not impl     AlertServiceCentre,
--not impl     InformServiceCentre,
--not impl     ReadyForSM
--not impl FROM MAP-ShortMessageServiceOperations {
--not impl    ccitt identified-organization (4) etsi (0) mobileDomain (0)
--not impl    gsm-Network (1) modules (3) map-ShortMessageServiceOperations (9)
--not impl    version8 (8)}
--not impl 
--not impl     PrepareGroupCall,
--not impl     ProcessGroupCallSignalling,
--not impl     ForwardGroupCallSignalling,
--not impl     SendGroupCallEndSignal
--not impl FROM MAP-Group-Call-Operations {
--not impl    ccitt identified-organization (4) etsi (0) mobileDomain (0)
--not impl    gsm-Network (1) modules (3) map-Group-Call-Operations (22)
--not impl    version8 (8)}
--not impl 
--not impl     ProvideSubscriberLocation,
--not impl     SendRoutingInfoForLCS,
--not impl     SubscriberLocationReport
--not impl FROM MAP-LocationServiceOperations {
--not impl    ccitt identified-organization (4) etsi (0) mobileDomain (0)
--not impl    gsm-Network (1) modules (3) map-LocationServiceOperations (24)
--not impl    version8 (8)}
--not impl 
--not impl SecureTransportClass1,
--not impl SecureTransportClass2,
--not impl SecureTransportClass3,
--not impl SecureTransportClass4
--not impl 
--not impl FROM MAP-SecureTransportOperations {
--not impl    ccitt identified-organization (4) etsi (0) mobileDomain (0)
--not impl    gsm-Network (1) modules (3) map-SecureTransportOperations (26)
--not impl    version8 (8)}
--not impl 
--not impl     SystemFailure,
--not impl     DataMissing,
--not impl     UnexpectedDataValue,
--not impl     FacilityNotSupported,
--not impl     UnknownSubscriber,
--not impl     NumberChanged,
--not impl     UnknownMSC,
--not impl     UnidentifiedSubscriber,
--not impl     UnknownEquipment,
--not impl     RoamingNotAllowed,
--not impl     IllegalSubscriber,
--not impl     IllegalEquipment,
--not impl     BearerServiceNotProvisioned,
--not impl     TeleserviceNotProvisioned,
--not impl     NoHandoverNumberAvailable,
--not impl     SubsequentHandoverFailure,
--not impl     TracingBufferFull,
--not impl     OR-NotAllowed,
--not impl     NoRoamingNumberAvailable,
--not impl     AbsentSubscriber,
--not impl     BusySubscriber,
--not impl     NoSubscriberReply,
--not impl     CallBarred,
--not impl     ForwardingViolation,
--not impl     ForwardingFailed,
--not impl     CUG-Reject, 
--not impl     ATI-NotAllowed,
--not impl     IllegalSS-Operation,
--not impl     SS-ErrorStatus,
--not impl     SS-NotAvailable,
--not impl     SS-SubscriptionViolation,
--not impl     SS-Incompatibility,
--not impl     UnknownAlphabet,
--not impl     USSD-Busy,
--not impl     PW-RegistrationFailure,
--not impl     NegativePW-Check,
--not impl     NumberOfPW-AttemptsViolation,
--not impl     SubscriberBusyForMT-SMS,
--not impl     SM-DeliveryFailure,
--not impl     MessageWaitingListFull,
--not impl     AbsentSubscriberSM,
--not impl     ResourceLimitation,
--not impl     NoGroupCallNumberAvailable,
--not impl     ShortTermDenial,
--not impl     LongTermDenial,
--not impl     IncompatibleTerminal,
--not impl     UnauthorizedRequestingNetwork,
--not impl     UnauthorizedLCSClient,
--not impl     PositionMethodFailure,
--not impl     UnknownOrUnreachableLCSClient,
--not impl     ATSI-NotAllowed,
--not impl     ATM-NotAllowed,
--not impl     InformationNotAvailable,
--not impl     MM-EventNotSupported,
--not impl     TargetCellOutsideGroupCallArea,
--not impl     SecureTransportError
--not impl 
--not impl 
--not impl 
--not impl FROM MAP-Errors {
--not impl    ccitt identified-organization (4) etsi (0) mobileDomain (0)
--not impl    gsm-Network (1) modules (3) map-Errors (10) version8 (8)}
--not impl ;
--not impl 
--not impl 
-- location registration operation codes
--not impl 
--not impl updateLocation  UpdateLocation ::= localValue 2
--not impl cancelLocation  CancelLocation ::= localValue 3
--not impl purgeMS  PurgeMS ::= localValue 67
--not impl sendIdentification  SendIdentification ::= localValue 55
--not impl 
--not impl 
-- handover operation codes
--not impl 
--not impl prepareHandover  PrepareHandover ::= localValue 68
--not impl sendEndSignal  SendEndSignal ::= localValue 29
--not impl processAccessSignalling  ProcessAccessSignalling ::= localValue 33
--not impl forwardAccessSignalling  ForwardAccessSignalling ::= localValue 34
--not impl prepareSubsequentHandover  PrepareSubsequentHandover ::=
--not impl     localValue 69
--not impl 
--not impl 
-- authentication operation codes
--not impl 
--not impl sendAuthenticationInfo  SendAuthenticationInfo ::= localValue 56 
--not impl authenticationFailureReport  AuthenticationFailureReport ::= localValue 15
--not impl 
--not impl 
-- IMEI MANAGEMENT operation codes
--not impl 
--not impl checkIMEI  CheckIMEI ::= localValue 43
--not impl 
--not impl 
-- subscriber management operation codes
--not impl 
--not impl insertSubscriberData  InsertSubscriberData ::= localValue 7
--not impl deleteSubscriberData  DeleteSubscriberData ::= localValue 8
--not impl 
--not impl 
-- fault recovery operation codes
--not impl 
--not impl reset  Reset ::= localValue 37
--not impl forwardCheckSS-Indication  ForwardCheckSS-Indication ::=
--not impl     localValue 38
--not impl restoreData  RestoreData ::= localValue 57
--not impl 
--not impl 
-- operation and maintenance operation codes
--not impl 
--not impl activateTraceMode  ActivateTraceMode ::= localValue 50
--not impl deactivateTraceMode  DeactivateTraceMode ::= localValue 51
--not impl sendIMSI  SendIMSI ::= localValue 58
--not impl 
--not impl 
-- call handling operation codes
--not impl 
--not impl sendRoutingInfo  SendRoutingInfo ::= localValue 22
--not impl provideRoamingNumber  ProvideRoamingNumber ::= localValue 4
--not impl resumeCallHandling  ResumeCallHandling ::= localValue 6 
--not impl provideSIWFSNumber  ProvideSIWFSNumber ::= localValue 31
--not impl sIWFSSignallingModify  SIWFSSignallingModify ::= localValue 32
--not impl setReportingState  SetReportingState ::= localValue 73
--not impl statusReport StatusReport ::= localValue 74
--not impl remoteUserFree RemoteUserFree ::= localValue 75
--not impl istAlert IST-Alert ::= localValue 87
--not impl istCommand IST-Command ::= localValue 88
--not impl 
--not impl 
-- supplementary service handling operation codes
--not impl 
--not impl registerSS  RegisterSS ::= localValue 10
--not impl eraseSS  EraseSS ::= localValue 11
--not impl activateSS  ActivateSS ::= localValue 12
--not impl deactivateSS  DeactivateSS ::= localValue 13
--not impl interrogateSS  InterrogateSS ::= localValue 14
--not impl processUnstructuredSS-Request  ProcessUnstructuredSS-Request ::=
--not impl     localValue 59
--not impl unstructuredSS-Request  UnstructuredSS-Request ::= localValue 60
--not impl unstructuredSS-Notify  UnstructuredSS-Notify ::= localValue 61
--not impl registerPassword  RegisterPassword ::= localValue 17
--not impl getPassword  GetPassword ::= localValue 18
--not impl registerCC-Entry  RegisterCC-Entry ::= localValue 76
--not impl eraseCC-Entry  EraseCC-Entry ::= localValue 77
--not impl 
--not impl 
-- short message service operation codes
--not impl 
--not impl sendRoutingInfoForSM  SendRoutingInfoForSM ::= localValue 45
--not impl mo-forwardSM  MO-ForwardSM ::= localValue 46
--not impl mt-forwardSM  MT-ForwardSM ::= localValue 44
--not impl reportSM-DeliveryStatus  ReportSM-DeliveryStatus ::= localValue 47
--not impl informServiceCentre  InformServiceCentre ::= localValue 63
--not impl alertServiceCentre  AlertServiceCentre ::= localValue 64
--not impl readyForSM  ReadyForSM ::= localValue 66
--not impl 
-- provide subscriber info operation codes
--not impl 
--not impl provideSubscriberInfo  ProvideSubscriberInfo ::= localValue 70
--not impl 
-- any time interrogation operation codes
--not impl 
--not impl anyTimeInterrogation  AnyTimeInterrogation ::= localValue 71
--not impl 
-- any time information handling operation codes
--not impl 
--not impl anyTimeSubscriptionInterrogation  AnyTimeSubscriptionInterrogation ::= localValue 62
--not impl anyTimeModification  AnyTimeModification ::= localValue 65
--not impl 
-- subscriber data modification notification operation codes
--not impl 
--not impl noteSubscriberDataModified  NoteSubscriberDataModified ::= localValue 5
--not impl 
-- supplementary service invocation notification operation codes
--not impl 
--not impl ss-InvocationNotification  SS-InvocationNotification ::= localValue 72
--not impl 
--not impl 
--Group Call operation codes
--not impl 
--not impl prepareGroupCall  PrepareGroupCall ::= localValue 39
--not impl sendGroupCallEndSignal  SendGroupCallEndSignal ::= localValue 40
--not impl processGroupCallSignalling  ProcessGroupCallSignalling ::= localValue 41
--not impl forwardGroupCallSignalling  ForwardGroupCallSignalling ::= localValue 42
--not impl 
--not impl 
-- gprs location updating operation codes
--not impl 
--not impl updateGprsLocation  UpdateGprsLocation ::= localValue 23
--not impl 
-- gprs location information retrieval operation codes
--not impl 
--not impl sendRoutingInfoForGprs  SendRoutingInfoForGprs ::= localValue 24
--not impl 
-- failure reporting operation codes
--not impl 
--not impl failureReport  FailureReport ::= localValue 25
--not impl 
-- GPRS notification operation codes
--not impl 
--not impl noteMsPresentForGprs  NoteMsPresentForGprs ::= localValue 26
--not impl 
-- Location service operation codes
--not impl 
--not impl provideSubscriberLocation  ProvideSubscriberLocation ::= localValue 83
--not impl sendRoutingInfoForLCS  SendRoutingInfoForLCS ::= localValue 85
--not impl subscriberLocationReport  SubscriberLocationReport ::= localValue 86
--not impl 
--not impl 
-- Mobility Management operation codes
--not impl 
--not impl noteMM-Event  NoteMM-Event ::= localValue 89
--not impl 
-- Secure transport operation codes
--not impl 
--not impl secureTransportClass1 SecureTransportClass1 ::= localValue 78
--not impl secureTransportClass2 SecureTransportClass2 ::= localValue 79
--not impl secureTransportClass3 SecureTransportClass3 ::= localValue 80
--not impl secureTransportClass4 SecureTransportClass4 ::= localValue 81
--not impl 
--not impl 
-- generic error codes
--not impl 
--not impl systemFailure  SystemFailure ::= localValue 34
--not impl dataMissing  DataMissing ::= localValue 35
--not impl unexpectedDataValue  UnexpectedDataValue ::= localValue 36
--not impl facilityNotSupported  FacilityNotSupported ::= localValue 21
--not impl incompatibleTerminal  IncompatibleTerminal ::= localValue 28
--not impl resourceLimitation  ResourceLimitation ::= localValue 51
--not impl 
--not impl 
-- identification and numbering error codes
--not impl 
--not impl unknownSubscriber  UnknownSubscriber ::= localValue 1
--not impl numberChanged  NumberChanged ::= localValue 44
--not impl unknownMSC  UnknownMSC ::= localValue 3
--not impl unidentifiedSubscriber  UnidentifiedSubscriber ::= localValue 5
--not impl unknownEquipment  UnknownEquipment ::= localValue 7
--not impl 
--not impl 
-- subscription error codes
--not impl 
--not impl roamingNotAllowed  RoamingNotAllowed ::= localValue 8
--not impl illegalSubscriber  IllegalSubscriber ::= localValue 9
--not impl illegalEquipment  IllegalEquipment ::= localValue 12
--not impl bearerServiceNotProvisioned  BearerServiceNotProvisioned ::=
--not impl     localValue 10
--not impl teleserviceNotProvisioned  TeleserviceNotProvisioned ::=
--not impl     localValue 11
--not impl 
--not impl 
-- handover error codes
--not impl 
--not impl noHandoverNumberAvailable  NoHandoverNumberAvailable ::=
--not impl     localValue 25
--not impl subsequentHandoverFailure  SubsequentHandoverFailure ::=
--not impl     localValue 26 
--not impl targetCellOutsideGroupCallArea  TargetCellOutsideGroupCallArea ::=
--not impl     localValue 42
--not impl 
--not impl 
--not impl 
-- operation and maintenance error codes
--not impl 
--not impl tracingBufferFull  TracingBufferFull ::= localValue 40
--not impl 
--not impl 
-- call handling error codes
--not impl 
--not impl noRoamingNumberAvailable  NoRoamingNumberAvailable ::= localValue 39
--not impl absentSubscriber  AbsentSubscriber ::= localValue 27
--not impl busySubscriber  BusySubscriber ::= localValue 45
--not impl noSubscriberReply  NoSubscriberReply ::= localValue 46
--not impl callBarred  CallBarred ::= localValue 13
--not impl forwardingFailed  ForwardingFailed ::= localValue 47
--not impl or-NotAllowed  OR-NotAllowed ::= localValue 48
--not impl forwardingViolation  ForwardingViolation ::= localValue 14
--not impl cug-Reject  CUG-Reject ::= localValue 15 
--not impl 
--not impl 
-- any time interrogation error codes
--not impl 
--not impl ati-NotAllowed  ATI-NotAllowed ::= localValue 49
--not impl 
-- any time information handling error codes
--not impl atsi-NotAllowed  ATSI-NotAllowed ::= localValue 60
--not impl atm-NotAllowed  ATM-NotAllowed ::= localValue 61
--not impl informationNotAvailable  InformationNotAvailable ::= localValue 62
--not impl 
--not impl 
-- Group Call error codes
--not impl noGroupCallNumberAvailable  NoGroupCallNumberAvailable ::= localValue 50
--not impl 
--not impl 
-- supplementary service error codes
--not impl 
--not impl illegalSS-Operation  IllegalSS-Operation ::= localValue 16
--not impl ss-ErrorStatus  SS-ErrorStatus ::= localValue 17
--not impl ss-NotAvailable  SS-NotAvailable ::= localValue 18
--not impl ss-SubscriptionViolation  SS-SubscriptionViolation ::= localValue 19
--not impl ss-Incompatibility  SS-Incompatibility ::= localValue 20
--not impl unknownAlphabet  UnknownAlphabet ::= localValue 71
--not impl ussd-Busy  USSD-Busy ::= localValue 72
--not impl pw-RegistrationFailure  PW-RegistrationFailure ::= localValue 37
--not impl negativePW-Check  NegativePW-Check ::= localValue 38
--not impl numberOfPW-AttemptsViolation  NumberOfPW-AttemptsViolation ::=
--not impl     localValue 43
--not impl shortTermDenial  ShortTermDenial ::= localValue 29
--not impl longTermDenial  LongTermDenial ::= localValue 30
--not impl 
--not impl 
-- short message service error codes
--not impl 
--not impl subscriberBusyForMT-SMS  SubscriberBusyForMT-SMS ::= localValue 31
--not impl sm-DeliveryFailure  SM-DeliveryFailure ::= localValue 32
--not impl messageWaitingListFull  MessageWaitingListFull ::= localValue 33
--not impl absentsubscriberSM  AbsentSubscriberSM ::= localValue 6
--not impl 
-- location service error codes
--not impl 
--not impl unauthorizedRequestingNetwork  UnauthorizedRequestingNetwork::= localValue 52
--not impl unauthorizedLCSClient  UnauthorizedLCSClient ::= localValue 53
--not impl positionMethodFailure  PositionMethodFailure ::= localValue 54
--not impl unknownOrUnreachableLCSClient  UnknownOrUnreachableLCSClient ::= localValue 58
--not impl 
--not impl 
-- Mobility Management error codes
--not impl mm-EventNotSupported  MM-EventNotSupported ::= localValue 59
--not impl 
-- Secure transport error codes
--not impl 
--not impl secureTransportError SecureTransportError ::= localValue 4
--not impl 
--not impl 
-- The following operation codes are reserved for operations
-- existing in previous versions of the protocol
--not impl 
-- Operation Name   AC used Oper. Code
-- 
-- sendParameters   map-ac infoRetrieval (14) version1 (1)  localValue 9
-- processUnstructuredSS-Data   map-ac networkFunctionalSs (18) version1 (1)    localValue 19
-- performHandover  map-ac handoverControl (11) version1 (1)    localValue 28
-- performSubsequentHandover    map-ac handoverControl (11) version1 (1)    localValue 30
-- noteInternalHandover map-ac handoverControl (11) version1 (1)    localValue 35
-- noteSubscriberPresent    map-ac mwdMngt (24) version1 (1)    localValue 48
-- alertServiceCentreWithoutResult  map-ac shortMsgAlert (23) version1 (1)  localValue 49
-- traceSubscriberActivity  map-ac handoverControl (11) version1 (1)    localValue 52
-- beginSubscriberActivity  map-ac networkFunctionalSs (18) version1 (1)    localValue 54

-- The following error codes are reserved for errors
-- existing in previous versions of the protocol

-- Error Name   AC used Error Code
-- 
-- unknownBaseStation   map-ac handoverControl (11) version1 (1)    localValue 2
-- invalidTargetBaseStation map-ac handoverControl (11) version1 (1)    localValue 23
-- noRadioResourceAvailable map-ac handoverControl (11) version1 (1)    localValue 24

--not impl 
--not impl 
--not impl END
--not impl 
--not impl  
--------------------------------------------------------------------------------
--------------------------------------------------------------------------------
--------------------------------------------------------------------------------


-- Module ----------------------------------------------------------------------
--------------------------------------------------------------------------------
-- MAP Mobile Service Operations.
--------------------------------------------------------------------------------
--------------------------------------------------------------------------------
 
--not impl MAP-MobileServiceOperations {
--not impl    ccitt identified-organization (4) etsi (0) mobileDomain (0)
--not impl    gsm-Network (1) modules (3) map-MobileServiceOperations (5)
--not impl    version8 (8)}
--not impl 
--not impl DEFINITIONS
--not impl 
--not impl ::=
--not impl 
--not impl BEGIN
--not impl 
--not impl EXPORTS
--not impl 
    -- location registration operations
--not impl     UpdateLocation,
--not impl     CancelLocation,
--not impl     PurgeMS,
--not impl     SendIdentification, 
--not impl 
    -- gprs location registration operations
--not impl     UpdateGprsLocation,
--not impl 
    -- subscriber information enquiry operations
--not impl     ProvideSubscriberInfo,
--not impl 
    -- any time information enquiry operations
--not impl     AnyTimeInterrogation,
--not impl 
    -- any time information handling operations
--not impl     AnyTimeSubscriptionInterrogation,
--not impl     AnyTimeModification, 
--not impl 
    -- subscriber data modification notification operations
--not impl     NoteSubscriberDataModified,
--not impl 
--not impl 
    -- handover operations
--not impl     PrepareHandover,
--not impl     SendEndSignal,
--not impl     ProcessAccessSignalling,
--not impl     ForwardAccessSignalling,
--not impl     PrepareSubsequentHandover,
--not impl 
    -- authentication management operations
--not impl     SendAuthenticationInfo, 
--not impl AuthenticationFailureReport,
--not impl 
    -- IMEI management operations
--not impl     CheckIMEI,
--not impl 
    -- subscriber management operations
--not impl     InsertSubscriberData,
--not impl     DeleteSubscriberData,
--not impl 
    -- fault recovery operations
--not impl     Reset,
--not impl     ForwardCheckSS-Indication,
--not impl     RestoreData,
--not impl 
-- gprs location information retrieval operations
--not impl     SendRoutingInfoForGprs,
--not impl     
    -- failure reporting operations
--not impl     FailureReport,
--not impl     
    -- gprs notification operations
--not impl     NoteMsPresentForGprs,
--not impl 
-- Mobility Management operations
--not impl NoteMM-Event
--not impl 
--not impl 
--not impl 
--not impl 
--not impl ;
--not impl 
--not impl IMPORTS
--not impl     OPERATION
--not impl FROM TCAPMessages {
--not impl    ccitt recommendation q 773 modules (2) messages (1) version2 (2)}
--not impl 
--not impl     SystemFailure,
--not impl     DataMissing,
--not impl     UnexpectedDataValue,
--not impl     UnknownSubscriber,
--not impl     UnknownMSC,
--not impl     UnidentifiedSubscriber,
--not impl     UnknownEquipment,
--not impl     RoamingNotAllowed, 
--not impl     ATI-NotAllowed,
--not impl     NoHandoverNumberAvailable,
--not impl     SubsequentHandoverFailure,
--not impl     AbsentSubscriber,
--not impl     MM-EventNotSupported,
--not impl     ATSI-NotAllowed,
--not impl     ATM-NotAllowed,
--not impl     BearerServiceNotProvisioned,
--not impl     TeleserviceNotProvisioned,
--not impl     CallBarred,
--not impl     IllegalSS-Operation,
--not impl     SS-ErrorStatus,
--not impl     SS-NotAvailable,
--not impl     SS-Incompatibility,
--not impl     SS-SubscriptionViolation,
--not impl     InformationNotAvailable,
--not impl     TargetCellOutsideGroupCallArea
--not impl 
--not impl 
--not impl FROM MAP-Errors {
--not impl    ccitt identified-organization (4) etsi (0) mobileDomain (0)
--not impl    gsm-Network (1) modules (3) map-Errors (10) version8 (8)}
--not impl 
--not impl     UpdateLocationArg,
--not impl     UpdateLocationRes,
--not impl     CancelLocationArg,
--not impl     CancelLocationRes, 
--not impl     PurgeMS-Arg, 
--not impl     PurgeMS-Res,
--not impl     SendIdentificationArg,
--not impl     SendIdentificationRes, 
--not impl     UpdateGprsLocationArg,
--not impl     UpdateGprsLocationRes,
--not impl     PrepareHO-Arg,
--not impl     PrepareHO-Res,
--not impl ForwardAccessSignalling-Arg,
--not impl ProcessAccessSignalling-Arg,
--not impl SendEndSignal-Arg,
--not impl SendEndSignal-Res,
--not impl PrepareSubsequentHO-Res,
--not impl     PrepareSubsequentHO-Arg,
--not impl     SendAuthenticationInfoArg,
--not impl     SendAuthenticationInfoRes, 
--not impl     AuthenticationFailureReportArg,
--not impl     AuthenticationFailureReportRes,
--not impl     EquipmentStatus,
--not impl     InsertSubscriberDataArg,
--not impl     InsertSubscriberDataRes,
--not impl     DeleteSubscriberDataArg,
--not impl     DeleteSubscriberDataRes,
--not impl     ResetArg,
--not impl     RestoreDataArg,
--not impl     RestoreDataRes,
--not impl     ProvideSubscriberInfoArg,
--not impl     ProvideSubscriberInfoRes,
--not impl     AnyTimeSubscriptionInterrogationArg,
--not impl     AnyTimeSubscriptionInterrogationRes,
--not impl     AnyTimeModificationArg,
--not impl     AnyTimeModificationRes,
--not impl     NoteSubscriberDataModifiedArg,
--not impl     NoteSubscriberDataModifiedRes,
--not impl     AnyTimeInterrogationArg,
--not impl     AnyTimeInterrogationRes,
--not impl     SendRoutingInfoForGprsArg,
--not impl     SendRoutingInfoForGprsRes,
--not impl     FailureReportArg,
--not impl     FailureReportRes,
--not impl     NoteMsPresentForGprsArg,
--not impl     NoteMsPresentForGprsRes,
--not impl     NoteMM-EventArg,
--not impl     NoteMM-EventRes
--not impl 
--not impl 
--not impl FROM MAP-MS-DataTypes {
--not impl    ccitt identified-organization (4) etsi (0) mobileDomain (0)
--not impl    gsm-Network (1) modules (3) map-MS-DataTypes (11) version8 (8)}
--not impl 
--not impl     IMEI
--not impl FROM MAP-CommonDataTypes {
--not impl    ccitt identified-organization (4) etsi (0) mobileDomain (0)
--not impl    gsm-Network (1) modules (3) map-CommonDataTypes (18) version8 (8)}
--not impl ;
--not impl 
--not impl 
-- location registration operations
--not impl 
--not impl UpdateLocation ::= OPERATION                
--Timer m
--not impl     ARGUMENT
--not impl         updateLocationArg   UpdateLocationArg
--not impl     RESULT
--not impl         updateLocationRes   UpdateLocationRes
--not impl     ERRORS {
--not impl         SystemFailure,
--not impl         DataMissing,
--not impl         UnexpectedDataValue,
--not impl         UnknownSubscriber,
--not impl         RoamingNotAllowed}
--not impl 
--not impl CancelLocation ::= OPERATION                
--Timer m
--not impl     ARGUMENT
--not impl         cancelLocationArg   CancelLocationArg
--not impl     RESULT
--not impl         cancelLocationRes   CancelLocationRes
            -- optional
--not impl     ERRORS {
--not impl         DataMissing,
--not impl         UnexpectedDataValue}
--not impl 
--not impl PurgeMS ::= OPERATION               
--Timer m
--not impl     ARGUMENT
--not impl         purgeMS-Arg PurgeMS-Arg
--not impl     RESULT
--not impl         purgeMS-Res PurgeMS-Res
            -- optional
--not impl     ERRORS{
--not impl         DataMissing,
--not impl         UnexpectedDataValue,
--not impl         UnknownSubscriber}
--not impl 
--not impl SendIdentification ::= OPERATION                
--Timer s
--not impl     ARGUMENT
--not impl         sendIdentificationArg       SendIdentificationArg
--not impl     RESULT
--not impl         sendIdentificationRes   SendIdentificationRes
--not impl     ERRORS {
--not impl         DataMissing,
--not impl         UnidentifiedSubscriber}
--not impl 
-- gprs location registration operations
--not impl 
--not impl UpdateGprsLocation ::= OPERATION                
--Timer m
--not impl     ARGUMENT
--not impl         updateGprsLocationArg   UpdateGprsLocationArg
--not impl     RESULT
--not impl         updateGprsLocationRes   UpdateGprsLocationRes
--not impl     ERRORS {
--not impl         SystemFailure,
--not impl         UnexpectedDataValue,
--not impl         UnknownSubscriber,
--not impl         RoamingNotAllowed}
--not impl 
-- subscriber information enquiry operations
--not impl 
--not impl ProvideSubscriberInfo ::= OPERATION             
--Timer m
--not impl     ARGUMENT
--not impl         provideSubscriberInfoArg    ProvideSubscriberInfoArg
--not impl     RESULT
--not impl         provideSubscriberInfoRes    ProvideSubscriberInfoRes
--not impl     ERRORS {
--not impl         DataMissing,
--not impl         UnexpectedDataValue}
--not impl 
-- any time information enquiry operations
--not impl 
--not impl AnyTimeInterrogation ::= OPERATION              
--Timer m
--not impl     ARGUMENT
--not impl         anyTimeInterrogationArg AnyTimeInterrogationArg
--not impl     RESULT
--not impl         anyTimeInterrogationRes AnyTimeInterrogationRes
--not impl     ERRORS {
--not impl         SystemFailure, 
--not impl         ATI-NotAllowed,
--not impl         DataMissing,
--not impl         UnexpectedDataValue,
--not impl         UnknownSubscriber}
--not impl 
-- any time information handling operations
--not impl 
--not impl AnyTimeSubscriptionInterrogation ::= OPERATION          
--Timer m
--not impl     ARGUMENT
--not impl         anyTimeSubscriptionInterrogationArg AnyTimeSubscriptionInterrogationArg
--not impl     RESULT
--not impl         anyTimeSubscriptionInterrogationRes AnyTimeSubscriptionInterrogationRes
--not impl     ERRORS {
--not impl         ATSI-NotAllowed,
--not impl         DataMissing,
--not impl         UnexpectedDataValue,
--not impl         UnknownSubscriber,
--not impl         BearerServiceNotProvisioned,
--not impl         TeleserviceNotProvisioned,
--not impl         CallBarred,
--not impl         IllegalSS-Operation,
--not impl         SS-NotAvailable,
--not impl         InformationNotAvailable}
--not impl 
--not impl AnyTimeModification ::= OPERATION               
--Timer m
--not impl     ARGUMENT
--not impl         anyTimeModificationArg  AnyTimeModificationArg
--not impl     RESULT
--not impl         anyTimeModificationRes  AnyTimeModificationRes
--not impl     ERRORS {
--not impl         ATM-NotAllowed,
--not impl         DataMissing,
--not impl         UnexpectedDataValue,
--not impl         UnknownSubscriber,
--not impl         BearerServiceNotProvisioned,
--not impl         TeleserviceNotProvisioned,
--not impl         CallBarred,
--not impl         IllegalSS-Operation,
--not impl         SS-SubscriptionViolation,
--not impl         SS-ErrorStatus,
--not impl         SS-Incompatibility,
--not impl         InformationNotAvailable}
--not impl 
-- subscriber data modification notification operations
--not impl 
--not impl NoteSubscriberDataModified ::= OPERATION                
--Timer m
--not impl     ARGUMENT
--not impl         noteSubscriberDataModifiedArg   NoteSubscriberDataModifiedArg
--not impl     RESULT
--not impl         noteSubscriberDataModifiedRes   NoteSubscriberDataModifiedRes
            -- optional
--not impl     ERRORS {
--not impl         DataMissing,
--not impl         UnexpectedDataValue,
--not impl         UnknownSubscriber}
--not impl 
--not impl 
-- handover operations
--not impl 
--not impl PrepareHandover ::= OPERATION               
--Timer m
--not impl     ARGUMENT
--not impl         prepareHO-Arg   PrepareHO-Arg
--not impl     RESULT
--not impl         prepareHO-Res   PrepareHO-Res
--not impl     ERRORS {
--not impl         SystemFailure,
--not impl         DataMissing,
--not impl         UnexpectedDataValue,
--not impl         NoHandoverNumberAvailable,
--not impl         TargetCellOutsideGroupCallArea }
--not impl 
--not impl SendEndSignal ::= OPERATION             
--Timer l
--not impl     ARGUMENT
--not impl         sendEndSignal-Arg   SendEndSignal-Arg
--not impl     RESULT
--not impl         sendEndSignal-Res   SendEndSignal-Res
--not impl     
--not impl 
--not impl ProcessAccessSignalling ::= OPERATION               
--Timer s
--not impl     ARGUMENT
--not impl         processAccessSignalling-Arg ProcessAccessSignalling-Arg
--not impl 
--not impl ForwardAccessSignalling ::= OPERATION               
--Timer s
--not impl     ARGUMENT
--not impl         forwardAccessSignalling-Arg ForwardAccessSignalling-Arg
--not impl 
--not impl PrepareSubsequentHandover ::= OPERATION             
--Timer m
--not impl     ARGUMENT
--not impl         prepareSubsequentHO-Arg PrepareSubsequentHO-Arg
--not impl     RESULT
--not impl         prepareSubsequentHO-Res PrepareSubsequentHO-Res
--not impl     ERRORS {
--not impl         UnexpectedDataValue,
--not impl         DataMissing,
--not impl         UnknownMSC,
--not impl         SubsequentHandoverFailure}
--not impl 
-- authentication management operations
--not impl 
--not impl SendAuthenticationInfo ::= OPERATION                
--Timer m
--not impl     ARGUMENT
--not impl         sendAuthenticationInfoArg   SendAuthenticationInfoArg
        -- optional
        -- if segmentation is used, sendAuthenticationInfoArg shall be present in the first
        -- segment and shall not be present in subsequent segments.  If received in
        -- subsequent segments it shall be discarded.
--not impl 
--not impl     RESULT
--not impl         sendAuthenticationInfoRes   SendAuthenticationInfoRes
        -- optional
--not impl     ERRORS {
--not impl         SystemFailure,
--not impl         DataMissing,
--not impl         UnexpectedDataValue,
--not impl         UnknownSubscriber}
--not impl 
--not impl AuthenticationFailureReport ::= OPERATION           
--Timer m
--not impl     ARGUMENT
--not impl         authenticationFailureReportArg  AuthenticationFailureReportArg
--not impl     RESULT
--not impl         authenticationFailureReportRes  AuthenticationFailureReportRes
        -- optional
--not impl     ERRORS {
--not impl         SystemFailure,
--not impl         UnexpectedDataValue,
--not impl         UnknownSubscriber}
--not impl 
-- IMEI management operations
--not impl 
--not impl CheckIMEI ::= OPERATION             
--Timer m
--not impl     ARGUMENT
--not impl         imei        IMEI
--not impl     RESULT
--not impl         equipmentStatus EquipmentStatus
--not impl     ERRORS {
--not impl         SystemFailure,
--not impl         DataMissing,
--not impl         UnknownEquipment}
--not impl 
-- subscriber management operations
--not impl 
--not impl InsertSubscriberData ::= OPERATION              
--Timer m
--not impl     ARGUMENT
--not impl         insertSubscriberDataArg InsertSubscriberDataArg
--not impl     RESULT
--not impl         insertSubscriberDataRes InsertSubscriberDataRes
        -- optional
--not impl     ERRORS {
--not impl         DataMissing,
--not impl         UnexpectedDataValue,
--not impl         UnidentifiedSubscriber}
--not impl 
--not impl DeleteSubscriberData ::= OPERATION              
--Timer m
--not impl     ARGUMENT
--not impl         deleteSubscriberDataArg DeleteSubscriberDataArg
--not impl     RESULT
--not impl         deleteSubscriberDataRes DeleteSubscriberDataRes
        -- optional
--not impl     ERRORS {
--not impl         DataMissing,
--not impl         UnexpectedDataValue,
--not impl         UnidentifiedSubscriber}
--not impl 
-- fault recovery operations
--not impl 
--not impl Reset ::= OPERATION             
--Timer m
--not impl     ARGUMENT
--not impl         resetArg    ResetArg
--not impl 
--not impl ForwardCheckSS-Indication ::= OPERATION         
--Timer s
--not impl 
--not impl RestoreData ::= OPERATION               
--Timer m
--not impl     ARGUMENT
--not impl         restoreDataArg  RestoreDataArg
--not impl     RESULT
--not impl         restoreDataRes  RestoreDataRes
--not impl     ERRORS {
--not impl         SystemFailure,
--not impl         DataMissing,
--not impl         UnexpectedDataValue,
--not impl         UnknownSubscriber}
--not impl 
-- gprs location information retrieval operations
--not impl 
--not impl SendRoutingInfoForGprs ::= OPERATION                
--Timer m
--not impl     ARGUMENT
--not impl         sendRoutingInfoForGprsArg   SendRoutingInfoForGprsArg
--not impl     RESULT
--not impl         sendRoutingInfoForGprsRes   SendRoutingInfoForGprsRes
--not impl     ERRORS {
--not impl         AbsentSubscriber,
--not impl         SystemFailure,
--not impl         DataMissing,
--not impl         UnexpectedDataValue,
--not impl         UnknownSubscriber}
--not impl 
-- failure reporting operations
--not impl 
--not impl FailureReport ::= OPERATION             
--Timer m
--not impl     ARGUMENT
--not impl         failureReportArg    FailureReportArg
--not impl     RESULT
--not impl         failureReportRes    FailureReportRes
            -- optional
--not impl     ERRORS {
--not impl         SystemFailure,
--not impl         DataMissing,
--not impl         UnexpectedDataValue,
--not impl         UnknownSubscriber}
--not impl 
-- gprs notification operations
--not impl 
--not impl NoteMsPresentForGprs ::= OPERATION              
--Timer m
--not impl     ARGUMENT
--not impl         noteMsPresentForGprsArg NoteMsPresentForGprsArg
--not impl     RESULT
--not impl         noteMsPresentForGprsRes NoteMsPresentForGprsRes
            -- optional
--not impl     ERRORS {
--not impl         SystemFailure,
--not impl         DataMissing,
--not impl         UnexpectedDataValue,
--not impl         UnknownSubscriber}
--not impl 
--not impl 
--not impl NoteMM-Event ::= OPERATION              
--Timer m
--not impl     ARGUMENT
--not impl         noteMM-EventArg NoteMM-EventArg
--not impl     RESULT
--not impl         noteMM-EventRes NoteMM-EventRes
--not impl     ERRORS {
--not impl         DataMissing,
--not impl         UnexpectedDataValue,
--not impl         UnknownSubscriber,
--not impl         MM-EventNotSupported}
--not impl 
--not impl END
--not impl  
--------------------------------------------------------------------------------
--------------------------------------------------------------------------------
--------------------------------------------------------------------------------


-- Module ----------------------------------------------------------------------
--------------------------------------------------------------------------------
-- MAP Operation and Maintenance Operations.
--------------------------------------------------------------------------------
--------------------------------------------------------------------------------
 
--not impl MAP-OperationAndMaintenanceOperations {
--not impl    ccitt identified-organization (4) etsi (0) mobileDomain (0)
--not impl    gsm-Network (1) modules (3) map-OperationAndMaintenanceOperations (6)
--not impl    version8 (8)}
--not impl 
--not impl DEFINITIONS
--not impl 
--not impl ::=
--not impl 
--not impl BEGIN
--not impl 
--not impl EXPORTS
--not impl     ActivateTraceMode,
--not impl     DeactivateTraceMode,
--not impl     SendIMSI
--not impl ;
--not impl 
--not impl IMPORTS
--not impl     OPERATION
--not impl FROM TCAPMessages {
--not impl    ccitt recommendation q 773 modules (2) messages (1) version2 (2)}
--not impl 
--not impl     SystemFailure,
--not impl     DataMissing,
--not impl     UnexpectedDataValue,
--not impl     FacilityNotSupported,
--not impl     UnknownSubscriber,
--not impl     UnidentifiedSubscriber,
--not impl     TracingBufferFull
--not impl FROM MAP-Errors {
--not impl    ccitt identified-organization (4) etsi (0) mobileDomain (0)
--not impl    gsm-Network (1) modules (3) map-Errors (10) version8 (8)}
--not impl 
--not impl     ActivateTraceModeArg,
--not impl     ActivateTraceModeRes,
--not impl     DeactivateTraceModeArg,
--not impl     DeactivateTraceModeRes
--not impl FROM MAP-OM-DataTypes {
--not impl    ccitt identified-organization (4) etsi (0) mobileDomain (0)
--not impl    gsm-Network (1) modules (3) map-OM-DataTypes (12) version8 (8)}
--not impl 
--not impl     ISDN-AddressString,
--not impl     IMSI
--not impl FROM MAP-CommonDataTypes {
--not impl    ccitt identified-organization (4) etsi (0) mobileDomain (0)
--not impl    gsm-Network (1) modules (3) map-CommonDataTypes (18) version8 (8)}
--not impl ;
--not impl 
--not impl 
--not impl ActivateTraceMode ::= OPERATION             
--Timer m
--not impl     ARGUMENT
--not impl         activateTraceModeArg    ActivateTraceModeArg
--not impl     RESULT
--not impl         activateTraceModeRes    ActivateTraceModeRes
        -- optional
--not impl     ERRORS {
--not impl         SystemFailure,
--not impl         DataMissing,
--not impl         UnexpectedDataValue,
--not impl         FacilityNotSupported,
--not impl         UnidentifiedSubscriber,
--not impl         TracingBufferFull}
--not impl 
--not impl DeactivateTraceMode ::= OPERATION               
--Timer m
--not impl     ARGUMENT
--not impl         deactivateTraceModeArg  DeactivateTraceModeArg
--not impl     RESULT
--not impl         deactivateTraceModeRes  DeactivateTraceModeRes
        -- optional
--not impl     ERRORS {
--not impl         SystemFailure,
--not impl         DataMissing,
--not impl         UnexpectedDataValue,
--not impl         FacilityNotSupported,
--not impl         UnidentifiedSubscriber}
--not impl 
--not impl SendIMSI ::= OPERATION              
--Timer m
--not impl     ARGUMENT
--not impl         msisdn  ISDN-AddressString
--not impl     RESULT
--not impl         imsi        IMSI
--not impl     ERRORS {
--not impl         DataMissing,
--not impl         UnexpectedDataValue,
--not impl         UnknownSubscriber}
--not impl 
--not impl END
--not impl  
--------------------------------------------------------------------------------
--------------------------------------------------------------------------------
--------------------------------------------------------------------------------


-- Module ----------------------------------------------------------------------
--------------------------------------------------------------------------------
-- MAP Call Handling Operations.
--------------------------------------------------------------------------------
--------------------------------------------------------------------------------

 
--not impl MAP-CallHandlingOperations {
--not impl    ccitt identified-organization (4) etsi (0) mobileDomain (0)
--not impl    gsm-Network (1) modules (3) map-CallHandlingOperations (7)
--not impl    version8 (8)}
--not impl 
--not impl DEFINITIONS
--not impl 
--not impl ::=
--not impl 
--not impl BEGIN
--not impl 
--not impl EXPORTS
--not impl     SendRoutingInfo,
--not impl     ProvideRoamingNumber,
--not impl     ResumeCallHandling,
--not impl     ProvideSIWFSNumber,
--not impl     SIWFSSignallingModify,
--not impl     SetReportingState,
--not impl     StatusReport,
--not impl     RemoteUserFree,
--not impl     IST-Alert,
--not impl     IST-Command
--not impl ;
--not impl 
--not impl IMPORTS
--not impl     OPERATION
--not impl FROM TCAPMessages {
--not impl    ccitt recommendation q 773 modules (2) messages (1) version2 (2)}
--not impl 
--not impl     SystemFailure,
--not impl     DataMissing,
--not impl     UnexpectedDataValue,
--not impl     FacilityNotSupported,
--not impl     OR-NotAllowed,
--not impl     UnknownSubscriber,
--not impl     NumberChanged,
--not impl     BearerServiceNotProvisioned,
--not impl     TeleserviceNotProvisioned,
--not impl     NoRoamingNumberAvailable,
--not impl     AbsentSubscriber,
--not impl     BusySubscriber,
--not impl     NoSubscriberReply,
--not impl     CallBarred,
--not impl     ForwardingViolation,
--not impl     ForwardingFailed,
--not impl     CUG-Reject,
--not impl     ResourceLimitation,
--not impl     IncompatibleTerminal,
--not impl     UnidentifiedSubscriber
--not impl 
--not impl FROM MAP-Errors {
--not impl    ccitt identified-organization (4) etsi (0) mobileDomain (0)
--not impl    gsm-Network (1) modules (3) map-Errors (10) version8 (8)}
--not impl     SendRoutingInfoArg,
--not impl     SendRoutingInfoRes,
--not impl     ProvideRoamingNumberArg,
--not impl     ProvideRoamingNumberRes,
--not impl     ResumeCallHandlingArg,
--not impl     ResumeCallHandlingRes,
--not impl     ProvideSIWFSNumberArg,
--not impl     ProvideSIWFSNumberRes,
--not impl     SIWFSSignallingModifyArg,
--not impl     SIWFSSignallingModifyRes,
--not impl     SetReportingStateArg,
--not impl     SetReportingStateRes,
--not impl     StatusReportArg,
--not impl     StatusReportRes,
--not impl     RemoteUserFreeArg,
--not impl     RemoteUserFreeRes,
--not impl     IST-AlertArg,
--not impl     IST-AlertRes,
--not impl     IST-CommandArg,
--not impl IST-CommandRes
--not impl FROM MAP-CH-DataTypes {
--not impl    ccitt identified-organization (4) etsi (0) mobileDomain (0)
--not impl    gsm-Network (1) modules (3) map-CH-DataTypes (13) version8 (8)}
--not impl 
--not impl ;
--not impl 
--not impl SendRoutingInfo ::= OPERATION               
--Timer m
-- The timer is set to the upper limit of the range if the GMSC supports pre-paging.
--not impl     ARGUMENT
--not impl         sendRoutingInfoArg  SendRoutingInfoArg
--not impl     RESULT
--not impl         sendRoutingInfoRes  SendRoutingInfoRes
--not impl     ERRORS {
--not impl         SystemFailure,
--not impl         DataMissing,
--not impl         UnexpectedDataValue,
--not impl         FacilityNotSupported,
--not impl         OR-NotAllowed,
--not impl         UnknownSubscriber,
--not impl         NumberChanged,
--not impl         BearerServiceNotProvisioned,
--not impl         TeleserviceNotProvisioned,
--not impl         AbsentSubscriber,
--not impl         BusySubscriber,
--not impl         NoSubscriberReply,
--not impl         CallBarred,
--not impl         CUG-Reject,
--not impl         ForwardingViolation}
--not impl 
--not impl ProvideRoamingNumber ::= OPERATION              
--Timer m
-- The timer is set to the upper limit of the range if the HLR supports pre-paging.
--not impl     ARGUMENT
--not impl         provideRoamingNumberArg ProvideRoamingNumberArg
--not impl     RESULT
--not impl         provideRoamingNumberRes ProvideRoamingNumberRes
--not impl     ERRORS {
--not impl         SystemFailure,
--not impl         DataMissing,
--not impl         UnexpectedDataValue,
--not impl         FacilityNotSupported,
--not impl         OR-NotAllowed,
--not impl         AbsentSubscriber,
--not impl         NoRoamingNumberAvailable}
--not impl 
--not impl ResumeCallHandling ::= OPERATION                
--Timer m
--not impl     ARGUMENT
--not impl         resumeCallHandlingArg   ResumeCallHandlingArg
--not impl     RESULT
--not impl         resumeCallHandlingRes   ResumeCallHandlingRes
        -- optional
--not impl     ERRORS {
--not impl         ForwardingFailed,
--not impl         OR-NotAllowed,
--not impl         UnexpectedDataValue,
--not impl         DataMissing }
--not impl 
--not impl ProvideSIWFSNumber ::= OPERATION                
--Timer m
--not impl     ARGUMENT
--not impl         provideSIWFSNumberArg   ProvideSIWFSNumberArg
--not impl     RESULT
--not impl         provideSIWFSNumberRes   ProvideSIWFSNumberRes
--not impl     ERRORS {
--not impl         ResourceLimitation,
--not impl         DataMissing,
--not impl         UnexpectedDataValue,
--not impl         SystemFailure}
--not impl 
--not impl SIWFSSignallingModify ::= OPERATION             
--Timer m
--not impl     ARGUMENT
--not impl         sIWFSSignallingModifyArg    SIWFSSignallingModifyArg
--not impl     RESULT
--not impl         sIWFSSignallingModifyRes    SIWFSSignallingModifyRes
        -- optional
--not impl     ERRORS {
--not impl         ResourceLimitation,
--not impl         DataMissing,
--not impl         UnexpectedDataValue,
--not impl         SystemFailure}
--not impl 
--not impl SetReportingState ::= OPERATION             
--Timer m
--not impl     ARGUMENT
--not impl         setReportingStateArg    SetReportingStateArg
--not impl     RESULT
--not impl         setReportingStateRes    SetReportingStateRes
        -- optional
--not impl     ERRORS {
--not impl         SystemFailure,
--not impl         UnidentifiedSubscriber,
--not impl         UnexpectedDataValue,
--not impl         DataMissing,
--not impl         ResourceLimitation,
--not impl         FacilityNotSupported}
--not impl 
--not impl StatusReport ::= OPERATION              
--Timer m
--not impl     ARGUMENT
--not impl         statusReportArg StatusReportArg
--not impl     RESULT
--not impl         statusReportRes StatusReportRes
        -- optional
--not impl     ERRORS {
--not impl         UnknownSubscriber,
--not impl         SystemFailure,
--not impl         UnexpectedDataValue,
--not impl         DataMissing}
--not impl 
--not impl RemoteUserFree ::= OPERATION                                   
--Timer ml
--not impl     ARGUMENT
--not impl         remoteUserFreeArg   RemoteUserFreeArg
--not impl     RESULT
--not impl         remoteUserFreeRes   RemoteUserFreeRes
--not impl     ERRORS {
--not impl         UnexpectedDataValue,
--not impl         DataMissing,
--not impl         IncompatibleTerminal,
--not impl         AbsentSubscriber,
--not impl         SystemFailure,
--not impl         BusySubscriber}
--not impl 
--not impl IST-Alert ::= OPERATION                                  
--Timer m
--not impl     ARGUMENT
--not impl         istAlertArg IST-AlertArg
--not impl     RESULT
--not impl         istAlertRes IST-AlertRes
        -- optional
--not impl     ERRORS {
--not impl         UnexpectedDataValue,
--not impl         ResourceLimitation,
--not impl         UnknownSubscriber,
--not impl         SystemFailure,
--not impl         FacilityNotSupported}
--not impl 
--not impl IST-Command ::= OPERATION                                    
--Timer m
--not impl     ARGUMENT
--not impl         istCommandArg   IST-CommandArg
--not impl     RESULT
--not impl         istCommandRes   IST-CommandRes
        -- optional
--not impl     ERRORS {
--not impl         UnexpectedDataValue,
--not impl         ResourceLimitation,
--not impl         UnknownSubscriber,
--not impl         SystemFailure,
--not impl         FacilityNotSupported}
--not impl 
--not impl END
--not impl  
--not impl 
--------------------------------------------------------------------------------
--------------------------------------------------------------------------------
--------------------------------------------------------------------------------


-- Module ----------------------------------------------------------------------
--------------------------------------------------------------------------------
-- MAP Supplementary Service Operations
--------------------------------------------------------------------------------
--------------------------------------------------------------------------------

 
--not impl MAP-SupplementaryServiceOperations {
--not impl    ccitt identified-organization (4) etsi (0) mobileDomain (0)
--not impl    gsm-Network (1) modules (3) map-SupplementaryServiceOperations (8)
--not impl    version8 (8)}
--not impl 
--not impl DEFINITIONS
--not impl 
--not impl ::=
--not impl 
--not impl BEGIN
--not impl 
--not impl EXPORTS
--not impl     RegisterSS,
--not impl     EraseSS,
--not impl     ActivateSS,
--not impl     DeactivateSS,
--not impl     InterrogateSS,
--not impl     ProcessUnstructuredSS-Request,
--not impl     UnstructuredSS-Request,
--not impl     UnstructuredSS-Notify,
--not impl     RegisterPassword,
--not impl     GetPassword,
--not impl     SS-InvocationNotification,
--not impl     RegisterCC-Entry,
--not impl     EraseCC-Entry
--not impl ;
--not impl 
--not impl IMPORTS
--not impl     OPERATION
--not impl FROM TCAPMessages {
--not impl    ccitt recommendation q 773 modules (2) messages (1) version2 (2)}
--not impl 
--not impl     SystemFailure,
--not impl     DataMissing,
--not impl     UnexpectedDataValue,
--not impl     UnknownSubscriber,
--not impl     BearerServiceNotProvisioned,
--not impl     TeleserviceNotProvisioned,
--not impl     CallBarred,
--not impl     IllegalSS-Operation,
--not impl     SS-ErrorStatus,
--not impl     SS-NotAvailable,
--not impl     SS-SubscriptionViolation,
--not impl     SS-Incompatibility,
--not impl     PW-RegistrationFailure,
--not impl     NegativePW-Check,
--not impl     NumberOfPW-AttemptsViolation,
--not impl     UnknownAlphabet,
--not impl     USSD-Busy,
--not impl     AbsentSubscriber,
--not impl     IllegalSubscriber,
--not impl     IllegalEquipment,
--not impl     ShortTermDenial,
--not impl     LongTermDenial,
--not impl     FacilityNotSupported
--not impl FROM MAP-Errors {
--not impl    ccitt identified-organization (4) etsi (0) mobileDomain (0)
--not impl    gsm-Network (1) modules (3) map-Errors (10) version8 (8)}
--not impl 
--not impl     RegisterSS-Arg,
--not impl     SS-Info,
--not impl     SS-ForBS-Code,
--not impl     InterrogateSS-Res,
--not impl     USSD-Arg,
--not impl     USSD-Res,
--not impl     Password,
--not impl     GuidanceInfo,
--not impl     SS-InvocationNotificationArg,
--not impl     SS-InvocationNotificationRes,
--not impl     RegisterCC-EntryArg,
--not impl     RegisterCC-EntryRes,
--not impl     EraseCC-EntryArg,
--not impl     EraseCC-EntryRes
--not impl FROM MAP-SS-DataTypes {
--not impl    ccitt identified-organization (4) etsi (0) mobileDomain (0)
--not impl    gsm-Network (1) modules (3) map-SS-DataTypes (14) version8 (8)}
--not impl 
--not impl     SS-Code
--not impl FROM MAP-SS-Code {
--not impl    ccitt identified-organization (4) etsi (0) mobileDomain (0)
--not impl    gsm-Network (1) modules (3) map-SS-Code (15) version8 (8)}
--not impl ;
--not impl 
--not impl 
-- supplementary service handling operations
--not impl 
--not impl RegisterSS ::= OPERATION                
--Timer m
--not impl     ARGUMENT
--not impl         registerSS-Arg  RegisterSS-Arg
--not impl     RESULT
--not impl         ss-Info SS-Info
        -- optional
--not impl     ERRORS {
--not impl         SystemFailure,
--not impl         DataMissing,
--not impl         UnexpectedDataValue,
--not impl         BearerServiceNotProvisioned,
--not impl         TeleserviceNotProvisioned,
--not impl         CallBarred,
--not impl         IllegalSS-Operation,
--not impl         SS-ErrorStatus,
--not impl         SS-Incompatibility}
--not impl 
--not impl EraseSS ::= OPERATION               
--Timer m
--not impl     ARGUMENT
--not impl         ss-ForBS    SS-ForBS-Code
--not impl     RESULT
--not impl         ss-Info SS-Info
        -- optional
--not impl     ERRORS {
--not impl         SystemFailure,
--not impl         DataMissing,
--not impl         UnexpectedDataValue,
--not impl         BearerServiceNotProvisioned,
--not impl         TeleserviceNotProvisioned,
--not impl         CallBarred,
--not impl         IllegalSS-Operation,
--not impl         SS-ErrorStatus
--not impl         }
--not impl 
--not impl ActivateSS ::= OPERATION                
--Timer m
--not impl     ARGUMENT
--not impl         ss-ForBS    SS-ForBS-Code
--not impl     RESULT
--not impl         ss-Info SS-Info
        -- optional
--not impl     ERRORS {
--not impl         SystemFailure,
--not impl         DataMissing,
--not impl         UnexpectedDataValue,
--not impl         BearerServiceNotProvisioned,
--not impl         TeleserviceNotProvisioned,
--not impl         CallBarred,
--not impl         IllegalSS-Operation,
--not impl         SS-ErrorStatus,
--not impl         SS-SubscriptionViolation,
--not impl         SS-Incompatibility,
--not impl         NegativePW-Check,
--not impl         NumberOfPW-AttemptsViolation}
--not impl 
--not impl DeactivateSS ::= OPERATION              
--Timer m
--not impl     ARGUMENT
--not impl         ss-ForBS    SS-ForBS-Code
--not impl     RESULT
--not impl         ss-Info SS-Info
        -- optional
--not impl     ERRORS {
--not impl         SystemFailure,
--not impl         DataMissing,
--not impl         UnexpectedDataValue,
--not impl         BearerServiceNotProvisioned,
--not impl         TeleserviceNotProvisioned,
--not impl         CallBarred,
--not impl         IllegalSS-Operation,
--not impl         SS-ErrorStatus,
--not impl         SS-SubscriptionViolation,
--not impl         NegativePW-Check,
--not impl         NumberOfPW-AttemptsViolation}
--not impl 
--not impl InterrogateSS ::= OPERATION             
--Timer m
--not impl     ARGUMENT
--not impl         ss-ForBS    SS-ForBS-Code
--not impl     RESULT
--not impl         interrogateSS-Res   InterrogateSS-Res
--not impl     ERRORS {
--not impl         SystemFailure,
--not impl         DataMissing,
--not impl         UnexpectedDataValue,
--not impl         BearerServiceNotProvisioned,
--not impl         TeleserviceNotProvisioned,
--not impl         CallBarred,
--not impl         IllegalSS-Operation,
--not impl         SS-NotAvailable}
--not impl 
--not impl ProcessUnstructuredSS-Request ::= OPERATION            
--Timer 10 minutes
--not impl     ARGUMENT
--not impl         ussd-Arg    USSD-Arg
--not impl     RESULT
--not impl         ussd-Res    USSD-Res
--not impl     ERRORS {
--not impl         SystemFailure,
--not impl         DataMissing,
--not impl         UnexpectedDataValue,
--not impl         UnknownAlphabet,
--not impl         CallBarred}
--not impl 
--not impl UnstructuredSS-Request ::= OPERATION                
--Timer ml
--not impl     ARGUMENT
--not impl         ussd-Arg    USSD-Arg
--not impl     RESULT
--not impl         ussd-Res    USSD-Res
        -- optional
--not impl     ERRORS {
--not impl         SystemFailure,
--not impl         DataMissing,
--not impl         UnexpectedDataValue,
--not impl         AbsentSubscriber,
--not impl         IllegalSubscriber,
--not impl         IllegalEquipment,
--not impl         UnknownAlphabet,
--not impl         USSD-Busy}
--not impl 
--not impl UnstructuredSS-Notify ::= OPERATION             
--Timer ml
--not impl     ARGUMENT
--not impl         ussd-Arg    USSD-Arg
--not impl     RESULT
--not impl     ERRORS {
--not impl         SystemFailure,
--not impl         DataMissing,
--not impl         UnexpectedDataValue,
--not impl         AbsentSubscriber,
--not impl         IllegalSubscriber,
--not impl         IllegalEquipment,
--not impl         UnknownAlphabet,
--not impl         USSD-Busy}
--not impl 
--not impl RegisterPassword ::= OPERATION              
--Timer ml
--not impl     ARGUMENT
--not impl         ss-Code SS-Code
--not impl     RESULT
--not impl         newPassword Password
--not impl     ERRORS {
--not impl         SystemFailure,
--not impl         DataMissing,
--not impl         UnexpectedDataValue,
--not impl         CallBarred,
--not impl         SS-SubscriptionViolation,
--not impl         PW-RegistrationFailure,
--not impl         NegativePW-Check,
--not impl         NumberOfPW-AttemptsViolation}
--not impl     LINKED {
--not impl         GetPassword}
--not impl 
--not impl GetPassword ::= OPERATION               
--Timer m
--not impl     ARGUMENT
--not impl         guidanceInfo    GuidanceInfo
--not impl     RESULT
--not impl         currentPassword Password
--not impl 
--not impl SS-InvocationNotification ::= OPERATION             
--Timer m
--not impl     ARGUMENT
--not impl         ss-InvocationNotificationArg        SS-InvocationNotificationArg
--not impl     RESULT
--not impl         ss-InvocationNotificationRes        SS-InvocationNotificationRes
        -- optional
--not impl     ERRORS {
--not impl         DataMissing,
--not impl         UnexpectedDataValue,
--not impl         UnknownSubscriber}
--not impl 
--not impl RegisterCC-Entry ::= OPERATION              
--Timer m
--not impl     ARGUMENT
--not impl         registerCC-EntryArg RegisterCC-EntryArg
--not impl     RESULT
--not impl         registerCC-EntryRes RegisterCC-EntryRes
--not impl     ERRORS {
--not impl         SystemFailure,
--not impl         DataMissing,
--not impl         UnexpectedDataValue,
--not impl         CallBarred,
--not impl         IllegalSS-Operation,
--not impl         SS-ErrorStatus,
--not impl         SS-Incompatibility,
--not impl         ShortTermDenial,
--not impl         LongTermDenial,
--not impl         FacilityNotSupported}
--not impl 
--not impl EraseCC-Entry ::= OPERATION             
--Timer m
--not impl     ARGUMENT
--not impl         eraseCC-EntryArg    EraseCC-EntryArg
--not impl     RESULT
--not impl         eraseCC-EntryRes    EraseCC-EntryRes
--not impl     ERRORS {
--not impl         SystemFailure,
--not impl         DataMissing,
--not impl         UnexpectedDataValue,
--not impl         CallBarred,
--not impl         IllegalSS-Operation,
--not impl         SS-ErrorStatus}
--not impl 
--not impl END
--not impl  
--not impl 
--------------------------------------------------------------------------------
--------------------------------------------------------------------------------
--------------------------------------------------------------------------------


-- Module ----------------------------------------------------------------------
--------------------------------------------------------------------------------
-- MAP Short Message Service Operations.
--------------------------------------------------------------------------------
--------------------------------------------------------------------------------

 
--not impl MAP-ShortMessageServiceOperations {
--not impl    ccitt identified-organization (4) etsi (0) mobileDomain (0)
--not impl    gsm-Network (1) modules (3) map-ShortMessageServiceOperations (9)
--not impl    version8 (8)}
--not impl 
--not impl DEFINITIONS
--not impl 
--not impl ::=
--not impl 
--not impl BEGIN
--not impl 
--not impl EXPORTS
--not impl     SendRoutingInfoForSM,
--not impl     MO-ForwardSM,
--not impl     MT-ForwardSM,
--not impl     ReportSM-DeliveryStatus,
--not impl     AlertServiceCentre,
--not impl     InformServiceCentre,
--not impl     ReadyForSM
--not impl ;
--not impl 
--not impl IMPORTS
--not impl     OPERATION
--not impl FROM TCAPMessages {
--not impl    ccitt recommendation q 773 modules (2) messages (1) version2 (2)}
--not impl 
--not impl     SystemFailure,
--not impl     DataMissing,
--not impl     UnexpectedDataValue,
--not impl     FacilityNotSupported,
--not impl     UnknownSubscriber,
--not impl     UnidentifiedSubscriber,
--not impl     IllegalSubscriber,
--not impl     IllegalEquipment,
--not impl     TeleserviceNotProvisioned,
--not impl     CallBarred,
--not impl     SubscriberBusyForMT-SMS,
--not impl     SM-DeliveryFailure,
--not impl     MessageWaitingListFull,
--not impl     AbsentSubscriberSM
--not impl FROM MAP-Errors {
--not impl    ccitt identified-organization (4) etsi (0) mobileDomain (0)
--not impl    gsm-Network (1) modules (3) map-Errors (10) version8 (8)}
--not impl 
--not impl     RoutingInfoForSM-Arg,
--not impl     RoutingInfoForSM-Res,
--not impl     MO-ForwardSM-Arg,
--not impl     MO-ForwardSM-Res,
--not impl     MT-ForwardSM-Arg,
--not impl     MT-ForwardSM-Res,
--not impl     ReportSM-DeliveryStatusArg,
--not impl     ReportSM-DeliveryStatusRes,
--not impl     AlertServiceCentreArg,
--not impl     InformServiceCentreArg,
--not impl     ReadyForSM-Arg,
--not impl     ReadyForSM-Res
--not impl FROM MAP-SM-DataTypes {
--not impl    ccitt identified-organization (4) etsi (0) mobileDomain (0)
--not impl    gsm-Network (1) modules (3) map-SM-DataTypes (16) version8 (8)}
--not impl 
--not impl 
--not impl 
--not impl ;
--not impl 
--not impl 
--not impl SendRoutingInfoForSM ::= OPERATION              
--Timer m
--not impl     ARGUMENT
--not impl         routingInfoForSM-Arg    RoutingInfoForSM-Arg
--not impl     RESULT
--not impl         routingInfoForSM-Res    RoutingInfoForSM-Res
--not impl     ERRORS {
--not impl         SystemFailure,
--not impl         DataMissing,
--not impl         UnexpectedDataValue,
--not impl         FacilityNotSupported,
--not impl         UnknownSubscriber,
--not impl         TeleserviceNotProvisioned,
--not impl         CallBarred,
--not impl         AbsentSubscriberSM}
--not impl 
--not impl MO-ForwardSM ::= OPERATION              
--Timer ml
--not impl     ARGUMENT
--not impl         mo-forwardSM-Arg    MO-ForwardSM-Arg
--not impl     RESULT
--not impl         mo-forwardSM-Res    MO-ForwardSM-Res
        -- optional
--not impl     ERRORS {
--not impl         SystemFailure,
--not impl         UnexpectedDataValue,
--not impl         FacilityNotSupported,
--not impl         SM-DeliveryFailure}
--not impl 
--not impl MT-ForwardSM ::= OPERATION              
--Timer ml
--not impl     ARGUMENT
--not impl         mt-forwardSM-Arg    MT-ForwardSM-Arg
--not impl     RESULT
--not impl         mt-forwardSM-Res    MT-ForwardSM-Res
        -- optional
--not impl     ERRORS {
--not impl         SystemFailure,
--not impl         DataMissing,
--not impl         UnexpectedDataValue,
--not impl         FacilityNotSupported,
--not impl         UnidentifiedSubscriber,
--not impl         IllegalSubscriber,
--not impl         IllegalEquipment,
--not impl         SubscriberBusyForMT-SMS,
--not impl         SM-DeliveryFailure,
--not impl         AbsentSubscriberSM}
--not impl 
--not impl ReportSM-DeliveryStatus ::= OPERATION           
--Timer s
--not impl     ARGUMENT
--not impl         reportSM-DeliveryStatusArg  ReportSM-DeliveryStatusArg
--not impl     RESULT
--not impl         reportSM-DeliveryStatusRes  ReportSM-DeliveryStatusRes
        -- optional
--not impl     ERRORS {
--not impl         DataMissing,
--not impl         UnexpectedDataValue,
--not impl         UnknownSubscriber,
--not impl         MessageWaitingListFull}
--not impl 
--not impl AlertServiceCentre ::= OPERATION                
--Timer s
--not impl     ARGUMENT
--not impl         alertServiceCentreArg   AlertServiceCentreArg
--not impl     RESULT
--not impl     ERRORS {
--not impl         SystemFailure,
--not impl         DataMissing,
--not impl         UnexpectedDataValue}
--not impl 
--not impl InformServiceCentre ::= OPERATION               
--Timer s
--not impl     ARGUMENT
--not impl         informServiceCentreArg  InformServiceCentreArg
--not impl 
--not impl ReadyForSM ::= OPERATION                
--Timer m
--not impl     ARGUMENT
--not impl         readyForSM-Arg  ReadyForSM-Arg
--not impl     RESULT
--not impl         readyForSM-Res  ReadyForSM-Res
        -- optional
--not impl     ERRORS {
--not impl         DataMissing,
--not impl         UnexpectedDataValue,
--not impl         FacilityNotSupported,
--not impl         UnknownSubscriber}
--not impl 
--not impl END
--not impl  
--not impl 
--------------------------------------------------------------------------------
--------------------------------------------------------------------------------
--------------------------------------------------------------------------------
--[CL] 29002-562.doc 17.6.6 Errors

-- Module ----------------------------------------------------------------------
--------------------------------------------------------------------------------
-- MAP Errors.
--------------------------------------------------------------------------------
--------------------------------------------------------------------------------
 
--not impl 
--not impl MAP-Errors {
--not impl    ccitt identified-organization (4) etsi (0) mobileDomain (0)
--not impl    gsm-Network (1) modules (3) map-Errors (10) version8 (8)}
--not impl 
--not impl DEFINITIONS
--not impl 
--not impl ::=
--not impl 
--not impl BEGIN
--not impl 
--not impl EXPORTS
--not impl 
    -- generic errors
--not impl     SystemFailure,
--not impl     DataMissing,
--not impl     UnexpectedDataValue,
--not impl     FacilityNotSupported,
--not impl     IncompatibleTerminal,
--not impl     ResourceLimitation,
--not impl 
    -- identification and numbering errors
--not impl     UnknownSubscriber,
--not impl     NumberChanged,
--not impl     UnknownMSC,
--not impl     UnidentifiedSubscriber,
--not impl     UnknownEquipment,
--not impl 
    -- subscription errors
--not impl     RoamingNotAllowed,
--not impl     IllegalSubscriber,
--not impl     IllegalEquipment,
--not impl     BearerServiceNotProvisioned,
--not impl     TeleserviceNotProvisioned,
--not impl 
    -- handover errors
--not impl     NoHandoverNumberAvailable,
--not impl     SubsequentHandoverFailure, 
--not impl     TargetCellOutsideGroupCallArea,
--not impl 
    -- operation and maintenance errors
--not impl     TracingBufferFull,
--not impl 
    -- call handling errors
--not impl     OR-NotAllowed,
--not impl     NoRoamingNumberAvailable,
--not impl     BusySubscriber,
--not impl     NoSubscriberReply,
--not impl     AbsentSubscriber,
--not impl     CallBarred,
--not impl     ForwardingViolation,
--not impl     ForwardingFailed,
--not impl     CUG-Reject,
--not impl 
    -- any time interrogation errors
--not impl     ATI-NotAllowed,
--not impl 
    -- any time information handling errors
--not impl     ATSI-NotAllowed,
--not impl     ATM-NotAllowed,
--not impl     InformationNotAvailable,
--not impl 
    -- supplementary service errors
--not impl     IllegalSS-Operation,
--not impl     SS-ErrorStatus,
--not impl     SS-NotAvailable,
--not impl     SS-SubscriptionViolation,
--not impl     SS-Incompatibility,
--not impl     UnknownAlphabet,
--not impl     USSD-Busy,
--not impl     PW-RegistrationFailure,
--not impl     NegativePW-Check,
--not impl     NumberOfPW-AttemptsViolation,
--not impl     ShortTermDenial,
--not impl     LongTermDenial,
--not impl 
    -- short message service errors
--not impl     SubscriberBusyForMT-SMS,
--not impl     SM-DeliveryFailure,
--not impl     MessageWaitingListFull,
--not impl     AbsentSubscriberSM,
--not impl 
    -- Group Call errors
--not impl     NoGroupCallNumberAvailable,
--not impl 
    -- location service errors
--not impl     UnauthorizedRequestingNetwork,
--not impl     UnauthorizedLCSClient,
--not impl     PositionMethodFailure,
--not impl     UnknownOrUnreachableLCSClient,
--not impl 
    -- Mobility Management errors
--not impl     MM-EventNotSupported,
--not impl 
    -- Secure transport errors
--not impl     SecureTransportError
--not impl 
--not impl 
--not impl ;
--not impl 
--not impl IMPORTS
--not impl     ERROR
--not impl FROM Remote-Operations-Information-Objects {joint-iso-itu-t 
--not impl   remote-operations(4)
--not impl   informationObjects(5) version1(0) }
--not impl 
--not impl     SS-Status
--not impl FROM MAP-SS-DataTypes {
--not impl    ccitt identified-organization (4) etsi (0) mobileDomain (0)
--not impl    gsm-Network (1) modules (3) map-SS-DataTypes (14) version8 (8)}
--not impl 
--not impl     SS-IncompatibilityCause,
--not impl     PW-RegistrationFailureCause,
--not impl     SM-DeliveryFailureCause,
--not impl     SystemFailureParam,
--not impl     DataMissingParam,
--not impl     UnexpectedDataParam,
--not impl     FacilityNotSupParam,
--not impl     UnknownSubscriberParam,
--not impl     NumberChangedParam,
--not impl     UnidentifiedSubParam,
--not impl     RoamingNotAllowedParam,
--not impl     IllegalSubscriberParam,
--not impl     IllegalEquipmentParam,
--not impl     BearerServNotProvParam,
--not impl     TeleservNotProvParam,
--not impl     TracingBufferFullParam,
--not impl     NoRoamingNbParam,
--not impl     OR-NotAllowedParam,
--not impl     AbsentSubscriberParam,
--not impl     BusySubscriberParam,
--not impl     NoSubscriberReplyParam,
--not impl     CallBarredParam,
--not impl     ForwardingViolationParam,
--not impl     ForwardingFailedParam,
--not impl     CUG-RejectParam, 
--not impl     ATI-NotAllowedParam,
--not impl     SubBusyForMT-SMS-Param,
--not impl     MessageWaitListFullParam,
--not impl     AbsentSubscriberSM-Param,
--not impl     ResourceLimitationParam,
--not impl     NoGroupCallNbParam,
--not impl     IncompatibleTerminalParam,
--not impl     ShortTermDenialParam,
--not impl     LongTermDenialParam,
--not impl     UnauthorizedRequestingNetwork-Param,
--not impl     UnauthorizedLCSClient-Param,
--not impl     PositionMethodFailure-Param,
--not impl UnknownOrUnreachableLCSClient-Param,
--not impl     MM-EventNotSupported-Param,
--not impl ATSI-NotAllowedParam,
--not impl ATM-NotAllowedParam,
--not impl IllegalSS-OperationParam,
--not impl SS-NotAvailableParam,
--not impl SS-SubscriptionViolationParam,
--not impl InformationNotAvailableParam,
--not impl TargetCellOutsideGCA-Param,
--not impl     SecureTransportErrorParam
--not impl 
--not impl 
--not impl 
--not impl 
--not impl FROM MAP-ER-DataTypes {
--not impl    ccitt identified-organization (4) etsi (0) mobileDomain (0)
--not impl    gsm-Network (1) modules (3) map-ER-DataTypes (17) version8 (8)}
--not impl ;
--not impl 
--not impl 
-- generic errors
--not impl 
--not impl SystemFailure ::= ERROR
--not impl     PARAMETER
--not impl         systemFailureParam  SystemFailureParam
        -- optional
--not impl 
--not impl DataMissing ::= ERROR
--not impl     PARAMETER
--not impl         dataMissingParam    DataMissingParam
        -- optional
        -- dataMissingParam must not be used in version <3
--not impl 
--not impl UnexpectedDataValue ::= ERROR
--not impl     PARAMETER
--not impl         unexpectedDataParam UnexpectedDataParam
        -- optional
        -- unexpectedDataParam must not be used in version <3
--not impl 
--not impl FacilityNotSupported ::= ERROR
--not impl     PARAMETER
--not impl         facilityNotSupParam FacilityNotSupParam
        -- optional
        -- facilityNotSupParam must not be used in version <3
--not impl 
--not impl IncompatibleTerminal ::= ERROR
--not impl     PARAMETER
--not impl         incompatibleTerminalParam   IncompatibleTerminalParam
        -- optional
--not impl 
--not impl ResourceLimitation ::= ERROR
--not impl     PARAMETER
--not impl         resourceLimitationParam ResourceLimitationParam
        -- optional
--not impl 
-- identification and numbering errors
--not impl 
--not impl UnknownSubscriber ::= ERROR
--not impl     PARAMETER
--not impl         unknownSubscriberParam  UnknownSubscriberParam
        -- optional
        -- unknownSubscriberParam must not be used in version <3
--not impl 
--not impl NumberChanged ::= ERROR
--not impl     PARAMETER
--not impl         numberChangedParam  NumberChangedParam
        -- optional
--not impl 
--not impl UnknownMSC ::= ERROR
--not impl 
--not impl UnidentifiedSubscriber ::= ERROR
--not impl     PARAMETER
--not impl         unidentifiedSubParam    UnidentifiedSubParam
        -- optional
        -- unidentifiedSubParam must not be used in version <3
--not impl 
--not impl UnknownEquipment ::= ERROR
--not impl 
--not impl 
-- subscription errors
--not impl 
--not impl RoamingNotAllowed ::= ERROR
--not impl     PARAMETER
--not impl         roamingNotAllowedParam  RoamingNotAllowedParam
--not impl 
--not impl IllegalSubscriber ::= ERROR
--not impl     PARAMETER
--not impl         illegalSubscriberParam  IllegalSubscriberParam
        -- optional
        -- illegalSubscriberParam must not be used in version <3
--not impl 
--not impl IllegalEquipment ::= ERROR
--not impl     PARAMETER
--not impl         illegalEquipmentParam   IllegalEquipmentParam
        -- optional
        -- illegalEquipmentParam must not be used in version <3
--not impl 
--not impl BearerServiceNotProvisioned ::= ERROR
--not impl     PARAMETER
--not impl         bearerServNotProvParam  BearerServNotProvParam
        -- optional
        -- bearerServNotProvParam must not be used in version <3
--not impl 
--not impl TeleserviceNotProvisioned ::= ERROR
--not impl     PARAMETER
--not impl         teleservNotProvParam    TeleservNotProvParam
        -- optional
        -- teleservNotProvParam must not be used in version <3
--not impl 
--not impl 
-- handover errors
--not impl 
--not impl NoHandoverNumberAvailable ::= ERROR
--not impl 
--not impl SubsequentHandoverFailure ::= ERROR
--not impl 
--not impl TargetCellOutsideGroupCallArea ::= ERROR 
--not impl     PARAMETER
--not impl         targetCellOutsideGCA-Param  TargetCellOutsideGCA-Param
        -- optional
--not impl 
--not impl 
-- operation and maintenance errors
--not impl 
--not impl TracingBufferFull ::= ERROR
--not impl     PARAMETER
--not impl         tracingBufferFullParam  TracingBufferFullParam
        -- optional
--not impl 
--not impl 
-- call handling errors
--not impl 
--not impl NoRoamingNumberAvailable ::= ERROR
--not impl     PARAMETER
--not impl         noRoamingNbParam    NoRoamingNbParam
        -- optional
--not impl 
--not impl AbsentSubscriber ::= ERROR
--not impl     PARAMETER
--not impl         absentSubscriberParam   AbsentSubscriberParam
        -- optional
        -- absentSubscriberParam must not be used in version <3
--not impl 
--not impl 
--not impl BusySubscriber ::= ERROR
--not impl     PARAMETER
--not impl         busySubscriberParam BusySubscriberParam
        -- optional
--not impl 
--not impl NoSubscriberReply ::= ERROR
--not impl     PARAMETER
--not impl         noSubscriberReplyParam  NoSubscriberReplyParam
        -- optional
--not impl 
--not impl CallBarred ::= ERROR
--not impl     PARAMETER
--not impl         callBarredParam CallBarredParam
        -- optional
--not impl 
--not impl ForwardingViolation ::= ERROR
--not impl     PARAMETER
--not impl         forwardingViolationParam    ForwardingViolationParam
        -- optional
--not impl 
--not impl ForwardingFailed ::= ERROR
--not impl     PARAMETER
--not impl         forwardingFailedParam   ForwardingFailedParam
        -- optional
--not impl 
--not impl CUG-Reject ::= ERROR
--not impl     PARAMETER
--not impl         cug-RejectParam CUG-RejectParam
        -- optional
--not impl 
--not impl OR-NotAllowed ::= ERROR
--not impl     PARAMETER
--not impl         or-NotAllowedParam  OR-NotAllowedParam
        -- optional
--not impl 
--not impl 
-- any time interrogation errors
--not impl ATI-NotAllowed ::= ERROR
--not impl     PARAMETER
--not impl         ati-NotAllowedParam ATI-NotAllowedParam
        -- optional
--not impl 
-- any time information handling errors
--not impl ATSI-NotAllowed ::= ERROR
--not impl     PARAMETER
--not impl         atsi-NotAllowedParam    ATSI-NotAllowedParam
        -- optional
--not impl 
--not impl ATM-NotAllowed ::= ERROR
--not impl     PARAMETER
--not impl         atm-NotAllowedParam ATM-NotAllowedParam
        -- optional
--not impl 
--not impl InformationNotAvailable ::= ERROR
--not impl     PARAMETER
--not impl         informationNotAvailableParam    InformationNotAvailableParam
        -- optional
--not impl 
--not impl 
-- supplementary service errors
--not impl 
--not impl IllegalSS-Operation ::= ERROR
--not impl     PARAMETER
--not impl         illegalSS-OperationParam    IllegalSS-OperationParam
        -- optional
        -- illegalSS-OperationParam must not be used in version <3
--not impl 
--not impl SS-ErrorStatus ::= ERROR
--not impl     PARAMETER
--not impl         ss-Status   SS-Status
        -- optional
--not impl 
--not impl SS-NotAvailable ::= ERROR
--not impl     PARAMETER
--not impl         ss-NotAvailableParam    SS-NotAvailableParam
        -- optional
        -- ss-NotAvailableParam must not be used in version <3
--not impl 
--not impl SS-SubscriptionViolation ::= ERROR
--not impl     PARAMETER
--not impl         ss-SubscriptionViolationParam   SS-SubscriptionViolationParam
        -- optional
        -- ss-NotAvailableParam must not be used in version <3
--not impl 
--not impl SS-Incompatibility ::= ERROR
--not impl     PARAMETER
--not impl         ss-IncompatibilityCause SS-IncompatibilityCause
        -- optional
--not impl 
--not impl UnknownAlphabet ::= ERROR
--not impl 
--not impl USSD-Busy ::= ERROR
--not impl 
--not impl PW-RegistrationFailure ::= ERROR
--not impl     PARAMETER
--not impl         pw-RegistrationFailureCause PW-RegistrationFailureCause
--not impl 
--not impl NegativePW-Check ::= ERROR
--not impl 
--not impl NumberOfPW-AttemptsViolation ::= ERROR
--not impl 
--not impl ShortTermDenial ::= ERROR
--not impl     PARAMETER
--not impl         shortTermDenialParam        ShortTermDenialParam
        -- optional
--not impl 
--not impl LongTermDenial ::= ERROR
--not impl     PARAMETER
--not impl         longTermDenialParam         LongTermDenialParam
        -- optional
--not impl 
--not impl 
-- short message service errors
--not impl 
--not impl SubscriberBusyForMT-SMS ::= ERROR
--not impl     PARAMETER
--not impl         subBusyForMT-SMS-Param  SubBusyForMT-SMS-Param
        -- optional
--not impl 
--not impl SM-DeliveryFailure ::= ERROR
--not impl     PARAMETER
--not impl         sm-DeliveryFailureCause SM-DeliveryFailureCause
--not impl 
--not impl MessageWaitingListFull ::= ERROR
--not impl     PARAMETER
--not impl         messageWaitListFullParam    MessageWaitListFullParam
        -- optional
--not impl 
--not impl AbsentSubscriberSM ::= ERROR
--not impl     PARAMETER
--not impl         absentSubscriberSM-Param    AbsentSubscriberSM-Param
        -- optional
--not impl 
-- Group Call errors
--not impl 
--not impl NoGroupCallNumberAvailable ::= ERROR
--not impl     PARAMETER
--not impl         noGroupCallNbParam  NoGroupCallNbParam
        -- optional
--not impl 
-- location service errors
--not impl 
--not impl UnauthorizedRequestingNetwork ::= ERROR
--not impl     PARAMETER
--not impl         unauthorizedRequestingNetwork-Param UnauthorizedRequestingNetwork-Param
        -- optional
--not impl 
--not impl UnauthorizedLCSClient ::= ERROR
--not impl     PARAMETER
--not impl         unauthorizedLCSClient-Param UnauthorizedLCSClient-Param
        -- optional
--not impl 
--not impl PositionMethodFailure ::= ERROR
--not impl     PARAMETER
--not impl         positionMethodFailure-Param PositionMethodFailure-Param
        -- optional
--not impl 
--not impl UnknownOrUnreachableLCSClient ::= ERROR
--not impl     PARAMETER
--not impl         unknownOrUnreachableLCSClient-Param  UnknownOrUnreachableLCSClient-Param
        -- optional
--not impl 
--not impl MM-EventNotSupported ::= ERROR
--not impl     PARAMETER
--not impl         mm-EventNotSupported-Param  MM-EventNotSupported-Param
        -- optional
--not impl 
    -- Secure transport errors
--not impl 
--not impl SecureTransportError ::= ERROR
--not impl     PARAMETER
--not impl         secureTransportErrorParam   SecureTransportErrorParam
--not impl 
--not impl 
--not impl END
--not impl  
--------------------------------------------------------------------------------
--------------------------------------------------------------------------------
--------------------------------------------------------------------------------
--[CL] 29002-562.doc 17.6.7 Group Call operations

-- Module ----------------------------------------------------------------------
--------------------------------------------------------------------------------
-- MAP Group Call Operations
--------------------------------------------------------------------------------
--------------------------------------------------------------------------------

 
--not impl MAP-Group-Call-Operations {
--not impl    ccitt identified-organization (4) etsi (0) mobileDomain (0)
--not impl    gsm-Network (1) modules (3) map-Group-Call-Operations (22)
--not impl    version8 (8)}
--not impl 
--not impl DEFINITIONS
--not impl 
--not impl ::=
--not impl 
--not impl BEGIN
--not impl 
--not impl EXPORTS
--not impl     PrepareGroupCall,
--not impl     SendGroupCallEndSignal,
--not impl     ForwardGroupCallSignalling,
--not impl     ProcessGroupCallSignalling
--not impl ;
--not impl 
--not impl IMPORTS
--not impl     OPERATION
--not impl FROM Remote-Operations-Information-Objects {
--not impl   joint-iso-itu-t remote-operations(4)
--not impl   informationObjects(5) version1(0)}
--not impl 
--not impl     SystemFailure,
--not impl     UnexpectedDataValue,
--not impl     NoGroupCallNumberAvailable
--not impl FROM MAP-Errors {
--not impl    ccitt identified-organization (4) etsi (0) mobileDomain (0)
--not impl    gsm-Network (1) modules (3) map-Errors (10) version8 (8)}
--not impl 
--not impl     PrepareGroupCallArg,
--not impl     PrepareGroupCallRes,
--not impl     SendGroupCallEndSignalArg,
--not impl     SendGroupCallEndSignalRes,
--not impl     ForwardGroupCallSignallingArg,
--not impl     ProcessGroupCallSignallingArg
--not impl FROM MAP-GR-DataTypes {
--not impl    ccitt identified-organization (4) etsi (0) mobileDomain (0)
--not impl    gsm-Network (1) modules (3) map-GR-DataTypes (23) version8 (8)}
--not impl 
--not impl 
--not impl 
--not impl ;
--not impl 
--not impl 
--not impl PrepareGroupCall ::= OPERATION              
--Timer m
--not impl     ARGUMENT
--not impl         prepareGroupCallArg PrepareGroupCallArg
--not impl     RESULT
--not impl         prepareGroupCallRes PrepareGroupCallRes
--not impl     ERRORS {
--not impl         SystemFailure,
--not impl         NoGroupCallNumberAvailable,
--not impl         UnexpectedDataValue}
--not impl 
--not impl SendGroupCallEndSignal ::= OPERATION                
--Timer l
--not impl     ARGUMENT
--not impl         sendGroupCallEndSignalArg   SendGroupCallEndSignalArg
--not impl     RESULT
--not impl         sendGroupCallEndSignalRes   SendGroupCallEndSignalRes
--not impl     
--not impl 
--not impl ProcessGroupCallSignalling ::= OPERATION                
--Timer s
--not impl     ARGUMENT
--not impl         processGroupCallSignallingArg   ProcessGroupCallSignallingArg
--not impl 
--not impl ForwardGroupCallSignalling ::= OPERATION                
--Timer s
--not impl     ARGUMENT
--not impl         forwardGroupCallSignallingArg   ForwardGroupCallSignallingArg
--not impl 
--not impl END
--not impl 
--not impl  
--------------------------------------------------------------------------------
--------------------------------------------------------------------------------
--------------------------------------------------------------------------------


-- Module ----------------------------------------------------------------------
--------------------------------------------------------------------------------
-- MAP Location Service Operations.
--------------------------------------------------------------------------------
--------------------------------------------------------------------------------
--[CL] 17.6.8 Location service operations

 
--not impl MAP-LocationServiceOperations {
--not impl    ccitt identified-organization (4) etsi (0) mobileDomain (0)
--not impl    gsm-Network (1) modules (3) map-LocationServiceOperations (24)
--not impl    version8 (8)}
--not impl 
--not impl DEFINITIONS
--not impl 
--not impl ::=
--not impl 
--not impl BEGIN
--not impl 
--not impl EXPORTS
--not impl     ProvideSubscriberLocation,
--not impl SendRoutingInfoForLCS,
--not impl SubscriberLocationReport
--not impl ;
--not impl 
--not impl IMPORTS
--not impl     OPERATION
--not impl FROM Remote-Operations-Information-Objects {
--not impl   joint-iso-itu-t remote-operations(4)
--not impl   informationObjects(5) version1(0)}
--not impl 
--not impl SystemFailure,
--not impl     DataMissing,
--not impl     UnexpectedDataValue,
--not impl     FacilityNotSupported,
--not impl     UnknownSubscriber,
--not impl     AbsentSubscriber,
--not impl     UnauthorizedRequestingNetwork,
--not impl     UnauthorizedLCSClient,
--not impl     PositionMethodFailure,
--not impl     ResourceLimitation,
--not impl     UnknownOrUnreachableLCSClient,
--not impl     UnidentifiedSubscriber,
--not impl     IllegalEquipment,
--not impl     IllegalSubscriber
--not impl FROM MAP-Errors {
--not impl    ccitt identified-organization (4) etsi (0) mobileDomain (0)
--not impl    gsm-Network (1) modules (3) map-Errors (10) version8 (8)}
--not impl 
--not impl     RoutingInfoForLCS-Arg,
--not impl     RoutingInfoForLCS-Res,
--not impl     ProvideSubscriberLocation-Arg,
--not impl     ProvideSubscriberLocation-Res,
--not impl     SubscriberLocationReport-Arg,
--not impl     SubscriberLocationReport-Res
--not impl FROM MAP-LCS-DataTypes {
--not impl    ccitt identified-organization (4) etsi (0) mobileDomain (0)
--not impl    gsm-Network (1) modules (3) map-LCS-DataTypes (25) version8 (8)}
--not impl ;
--not impl 
--not impl SendRoutingInfoForLCS ::= OPERATION             
--Timer m
--not impl     ARGUMENT
--not impl         routingInfoForLCS-Arg   RoutingInfoForLCS-Arg
--not impl     RESULT
--not impl         routingInfoForLCS-Res   RoutingInfoForLCS-Res
--not impl     ERRORS {
--not impl         SystemFailure,
--not impl         DataMissing,
--not impl         UnexpectedDataValue,
--not impl         FacilityNotSupported,
--not impl         UnknownSubscriber,
--not impl         AbsentSubscriber,
--not impl         UnauthorizedRequestingNetwork }
--not impl 
--not impl ProvideSubscriberLocation ::= OPERATION             
--Timer ml
--not impl     ARGUMENT
--not impl         provideSubscriberLocation-Arg   ProvideSubscriberLocation-Arg
--not impl     RESULT
--not impl         provideSubscriberLocation-Res   ProvideSubscriberLocation-Res
--not impl     ERRORS {
--not impl         SystemFailure,
--not impl         DataMissing,
--not impl         UnexpectedDataValue,
--not impl         FacilityNotSupported,
--not impl         UnidentifiedSubscriber,
--not impl         IllegalSubscriber,
--not impl         IllegalEquipment,
--not impl         AbsentSubscriber,
--not impl         UnauthorizedRequestingNetwork,
--not impl         UnauthorizedLCSClient,
--not impl         PositionMethodFailure }
--not impl 
--not impl SubscriberLocationReport ::= OPERATION              
--Timer m
--not impl     ARGUMENT
--not impl         subscriberLocationReport-Arg    SubscriberLocationReport-Arg
--not impl     RESULT
--not impl         subscriberLocationReport-Res    SubscriberLocationReport-Res
--not impl     ERRORS {
--not impl         SystemFailure,
--not impl         DataMissing,
--not impl         ResourceLimitation,
--not impl         UnexpectedDataValue,
--not impl         UnknownSubscriber,
--not impl         UnauthorizedRequestingNetwork,
--not impl         UnknownOrUnreachableLCSClient}
--not impl 
--not impl 
--not impl END
--not impl  

--------------------------------------------------------------------------------
--------------------------------------------------------------------------------
--------------------------------------------------------------------------------
--[CL] 29002-562.doc 17.6.9 Secure transport operations

-- Module ----------------------------------------------------------------------
--------------------------------------------------------------------------------
-- MAP Secure Transport Operations.
--------------------------------------------------------------------------------
--------------------------------------------------------------------------------

 
--not impl MAP-SecureTransportOperations {
--not impl    ccitt identified-organization (4) etsi (0) mobileDomain (0)
--not impl    gsm-Network (1) modules (3) map-SecureTransportOperations (26)
--not impl    version8 (8)}
--not impl 
--not impl DEFINITIONS
--not impl 
--not impl ::=
--not impl 
--not impl BEGIN
--not impl 
--not impl EXPORTS
--not impl     SecureTransportClass1,
--not impl     SecureTransportClass2,
--not impl     SecureTransportClass3,
--not impl     SecureTransportClass4
--not impl ;
--not impl 
--not impl IMPORTS
--not impl     OPERATION
--not impl FROM Remote-Operations-Information-Objects {
--not impl   joint-iso-itu-t remote-operations(4)
--not impl   informationObjects(5) version1(0)}
--not impl 
--not impl     DataMissing,
--not impl     SecureTransportError,
--not impl     UnexpectedDataValue
--not impl 
--not impl FROM MAP-Errors {
--not impl    ccitt identified-organization (4) etsi (0) mobileDomain (0)
--not impl    gsm-Network (1) modules (3) map-Errors (10) version8 (8)}
--not impl 
--not impl     SecureTransportArg,
--not impl     SecureTransportRes
--not impl 
--not impl FROM MAP-ST-DataTypes {
--not impl    ccitt identified-organization (4) etsi (0) mobileDomain (0)
--not impl    gsm-Network (1) modules (3) map-ST-DataTypes (27) version8 (8)}
--not impl ;
--not impl 
--not impl SecureTransportClass1 ::= OPERATION         
--Timer shall be the same as for the securely transported operation
--not impl     ARGUMENT
--not impl         secureTransportArg  SecureTransportArg
--not impl     RESULT
--not impl         secureTransportRes  SecureTransportRes
--not impl     ERRORS {
--not impl         SecureTransportError,
--not impl         DataMissing,
--not impl         UnexpectedDataValue}
--not impl 
--not impl SecureTransportClass2 ::= OPERATION         
--Timer shall be the same as for the securely transported operation
--not impl     ARGUMENT
--not impl         secureTransportArg  SecureTransportArg
--not impl     ERRORS {
--not impl         SecureTransportError,
--not impl         DataMissing,
--not impl         UnexpectedDataValue}
--not impl 
--not impl SecureTransportClass3 ::= OPERATION         
--Timer shall be the same as for the securely transported operation
--not impl     ARGUMENT
--not impl         secureTransportArg  SecureTransportArg
--not impl     RESULT
--not impl         secureTransportRes  SecureTransportRes
--not impl 
--not impl SecureTransportClass4 ::= OPERATION         
--Timer shall be the same as for the securely transported operation
--not impl     ARGUMENT
--not impl         secureTransportArg  SecureTransportArg  
--not impl 
--not impl 
--not impl END
--not impl 
--------------------------------------------------------------------------------
--------------------------------------------------------------------------------
--------------------------------------------------------------------------------
--[CL] 29002-562.doc 17.7.1 Mobile Service data types

-- Module ----------------------------------------------------------------------
--------------------------------------------------------------------------------
-- MAP MS Data Types.
--------------------------------------------------------------------------------
--------------------------------------------------------------------------------
 
--not used MAP-MS-DataTypes {
--not used    ccitt identified-organization (4) etsi (0) mobileDomain (0)
--not used    gsm-Network (1) modules (3) map-MS-DataTypes (11) version8 (8)}
--not used 
--not used DEFINITIONS
--not used 
--not used IMPLICIT TAGS
--not used 
--not used ::=
--not used 
--not used BEGIN
--not used 
--not used EXPORTS
--not used 
    -- location registration types
--not used     UpdateLocationArg,
--not used     UpdateLocationRes,
--not used     CancelLocationArg,
--not used     CancelLocationRes, 
--not used     PurgeMS-Arg, 
--not used     PurgeMS-Res,
--not used     SendIdentificationArg,
--not used     SendIdentificationRes, 
--not used     UpdateGprsLocationArg,
--not used     UpdateGprsLocationRes,
--not used     IST-SupportIndicator,
--not used     SupportedLCS-CapabilitySets,

--not used 
    -- gprs location registration types
--not used     GSN-Address,
--not used 
    -- handover types
--not used     ForwardAccessSignalling-Arg,
--not used     PrepareHO-Arg,
--not used     PrepareHO-Res,
--not used     PrepareSubsequentHO-Arg, 
--not used     PrepareSubsequentHO-Res,
--not used     ProcessAccessSignalling-Arg,
--not used     SendEndSignal-Arg,
--not used     SendEndSignal-Res,
--not used 
--not used 
    -- authentication management types
--not used     SendAuthenticationInfoArg,
--not used     SendAuthenticationInfoRes, 
--not used     AuthenticationFailureReportArg,
--not used AuthenticationFailureReportRes,
--not used 
    -- security management types
--not used     Kc,
--not used
-- equipment management types
--not used     CheckIMEI-Arg,
--not used     CheckIMEI-Res,
--not used
--not used 
    -- subscriber management types
--not used     InsertSubscriberDataArg,
--not used     InsertSubscriberDataRes,
--not used     LSAIdentity,
--not used     DeleteSubscriberDataArg,
--not used     DeleteSubscriberDataRes,
--not used     Ext-QoS-Subscribed,
--not used     SubscriberData,
--not used     ODB-Data,
--not used     SubscriberStatus,
--not used     ZoneCodeList,
--not used     maxNumOfZoneCodes, 
--not used     O-CSI, 
--not used D-CSI,
--not used     O-BcsmCamelTDPCriteriaList, 
--not used     T-BCSM-CAMEL-TDP-CriteriaList,
--not used     SS-CSI,
--not used     ServiceKey,
--not used     DefaultCallHandling,
--not used     CamelCapabilityHandling,
--not used     BasicServiceCriteria,
--not used     SupportedCamelPhases,
--not used     OfferedCamel4CSIs,
--not used     OfferedCamel4Functionalities,
--not used     maxNumOfCamelTDPData,
--not used     CUG-Index,
--not used     CUG-Info,
--not used     CUG-Interlock,
--not used     InterCUG-Restrictions,
--not used     IntraCUG-Options,
--not used     NotificationToMSUser,
--not used     QoS-Subscribed,
--not used IST-AlertTimerValue,
--not used     T-CSI,
--not used     T-BcsmTriggerDetectionPoint,
--not used     APN,
--not used 
    -- fault recovery types
--not used     ResetArg,
--not used     RestoreDataArg,
--not used     RestoreDataRes,
--not used 
-- provide subscriber info types 
--not used GeographicalInformation, 
--not used MS-Classmark2,
--not used GPRSMSClass,
--not used
    -- subscriber information enquiry types
--not used     ProvideSubscriberInfoArg,
--not used     ProvideSubscriberInfoRes,
--not used     SubscriberInfo,
--not used     LocationInformation,
--not used     LocationInformationGPRS,
--not used     RAIdentity,
--not used     SubscriberState,
--not used     GPRSChargingID,
--not used 
    -- any time information enquiry types
--not used     AnyTimeInterrogationArg,
--not used     AnyTimeInterrogationRes,
--not used 
    -- any time information handling types
--not used     AnyTimeSubscriptionInterrogationArg,
--not used     AnyTimeSubscriptionInterrogationRes,
--not used     AnyTimeModificationArg,
--not used     AnyTimeModificationRes,
--not used 
    -- subscriber data modification notification types
--not used     NoteSubscriberDataModifiedArg,
--not used     NoteSubscriberDataModifiedRes,
--not used 
    -- gprs location information retrieval types
--not used     SendRoutingInfoForGprsArg,
--not used     SendRoutingInfoForGprsRes,
--not used 
    -- failure reporting types
--not used     FailureReportArg,
--not used     FailureReportRes,
--not used 
    -- gprs notification types
--not used     NoteMsPresentForGprsArg,
--not used     NoteMsPresentForGprsRes,
--not used 
    -- Mobility Management types
--not used NoteMM-EventArg,
--not used     NoteMM-EventRes
--not used 
--not used 
--not used 
--not used ;
--not used 
--not used IMPORTS
--not used     maxNumOfSS,
--not used     SS-SubscriptionOption,
--not used     SS-List,
--not used     SS-ForBS-Code,
--not used     Password
--not used FROM MAP-SS-DataTypes {
--not used    ccitt identified-organization (4) etsi (0) mobileDomain (0)
--not used    gsm-Network (1) modules (3) map-SS-DataTypes (14) version8 (8)}
--not used 
--not used     SS-Code
--not used FROM MAP-SS-Code {
--not used    ccitt identified-organization (4) etsi (0) mobileDomain (0)
--not used    gsm-Network (1) modules (3) map-SS-Code (15) version8 (8)}
--not used 
--not used     Ext-BearerServiceCode
--not used FROM MAP-BS-Code {
--not used    ccitt identified-organization (4) etsi (0) mobileDomain (0)
--not used    gsm-Network (1) modules (3) map-BS-Code (20) version8 (8)}
--not used 
--not used     Ext-TeleserviceCode
--not used FROM MAP-TS-Code {
--not used    ccitt identified-organization (4) etsi (0) mobileDomain (0)
--not used    gsm-Network (1) modules (3) map-TS-Code (19) version8 (8)}
--not used 
--not used 
--not used     AddressString,
--not used ISDN-AddressString, 
--not used     ISDN-SubaddressString, 
--not used     FTN-AddressString,
--not used     AccessNetworkSignalInfo,
--not used     IMSI,
--not used     IMEI, 
--not used     TMSI,
--not used     HLR-List,
--not used     LMSI,
--not used     Identity,
--not used     GlobalCellId,
--not used     CellGlobalIdOrServiceAreaIdOrLAI,
--not used     Ext-BasicServiceCode,
--not used     NAEA-PreferredCI,
--not used     EMLPP-Info, 
--not used     MC-SS-Info,
--not used     SubscriberIdentity,
--not used     AgeOfLocationInformation,
--not used     LCSClientExternalID,
--not used     LCSClientInternalID,
--not used     Ext-SS-Status
--not used     LCSServiceTypeID,
--not used     ASCI-CallReference
--not used 
--not used 
--not used 
--not used FROM MAP-CommonDataTypes {
--not used    ccitt identified-organization (4) etsi (0) mobileDomain (0)
--not used    gsm-Network (1) modules (3) map-CommonDataTypes (18) version8 (8)}
--not used 
--not used     ExtensionContainer
--not used FROM MAP-ExtensionDataTypes {
--not used    ccitt identified-organization (4) etsi (0) mobileDomain (0)
--not used    gsm-Network (1) modules (3) map-ExtensionDataTypes (21) version8 (8)}
--not used 
--not used     AbsentSubscriberDiagnosticSM
--not used FROM MAP-ER-DataTypes {
--not used    ccitt identified-organization (4) etsi (0) mobileDomain (0)
--not used    gsm-Network (1) modules (3) map-ER-DataTypes (17) version8 (8)}
--not used 
--not used 
--not used ;
--not used 
--not used 
-- location registration types

UpdateLocationArg ::= SEQUENCE {
    imsi            IMSI,
    msc-Number  [1] ISDN-AddressString,
    vlr-Number  ISDN-AddressString,
    lmsi            [10] LMSI   OPTIONAL,
    extensionContainer  ExtensionContainer  OPTIONAL,
    ... ,
    vlr-Capability  [6] VLR-Capability  OPTIONAL,
    informPreviousNetworkEntity	[11]	NULL		OPTIONAL,
    cs-LCS-NotSupportedByUE	[12]	NULL		OPTIONAL, 
    v-gmlc-Address	[2]	GSN-Address	OPTIONAL,
    add-info		[13] ADD-Info
}

VLR-Capability ::= SEQUENCE{
    supportedCamelPhases    [0] SupportedCamelPhases    OPTIONAL,
    extensionContainer          ExtensionContainer 	 OPTIONAL,
    ... ,
    solsaSupportIndicator   [2] NULL		        OPTIONAL,
    istSupportIndicator [1] IST-SupportIndicator    OPTIONAL,
    superChargerSupportedInServingNetworkEntity [3] SuperChargerInfo    OPTIONAL,
    longFTN-Supported   [4] NULL        OPTIONAL,
    supportedLCS-CapabilitySets	[5]	SupportedLCS-CapabilitySets	OPTIONAL,
    offeredCamel4CSIs	[6] OfferedCamel4CSIs	OPTIONAL }

SuperChargerInfo ::= CHOICE {
    sendSubscriberData  [0] NULL,
    subscriberDataStored    [1] AgeIndicator }

AgeIndicator ::= OCTET STRING (SIZE (1..6))
    -- The internal structure of this parameter is implementation specific.


IST-SupportIndicator ::=  ENUMERATED {
    basicISTSupported   (0),
    istCommandSupported (1),
    ...}
-- exception handling:
-- reception of values > 1 shall be mapped to ' istCommandSupported '

SupportedLCS-CapabilitySets ::= BIT STRING {
	lcsCapabilitySet1 (0),
	lcsCapabilitySet2 (1),
	lcsCapabilitySet3 (2) } (SIZE (2..16)) 
-- Core network signalling capability set1 indicates LCS Release98 or Release99 version.
-- Core network signalling capability set2 indicates LCS Release4.
-- Core network signalling capability set3 indicates LCS Release5 or later version.
-- A node shall mark in the BIT STRING all LCS capability sets it supports. 
-- If no bit is set then the sending node does not support LCS.
-- If the parameter is not sent by an VLR then the VLR may support at most capability set1.
-- If the parameter is not sent by an SGSN then no support for LCS is assumed.
-- An SGSN is not allowed to indicate support of capability set1.
-- Other bits than listed above shall be discarded.

UpdateLocationRes ::= SEQUENCE {
    hlr-Number  ISDN-AddressString,

    extensionContainer  ExtensionContainer  OPTIONAL,
    ...,
    add-Capability	NULL			OPTIONAL 
 }
ADD-Info ::= SEQUENCE {
	imeisv		[0] IMEI,
	skipSubscriberDataUpdate	[1] NULL		OPTIONAL,
	...}

CancelLocationArg ::= [3] SEQUENCE {
    identity        Identity,
    cancellationType    CancellationType    OPTIONAL,
    extensionContainer  ExtensionContainer  OPTIONAL,
    ...}


CancellationType ::= ENUMERATED {
    updateProcedure (0),
    subscriptionWithdraw    (1),
    ...}
    -- The HLR shall not send values other than listed above


CancelLocationRes ::= SEQUENCE {
    extensionContainer  ExtensionContainer  OPTIONAL,
    ...}

PurgeMS-Arg ::= [3] SEQUENCE {
    imsi            IMSI,
    vlr-Number  [0] ISDN-AddressString  OPTIONAL,
    sgsn-Number [1] ISDN-AddressString  OPTIONAL,
    extensionContainer  ExtensionContainer  OPTIONAL,
    ...}

PurgeMS-Res ::= SEQUENCE {
    freezeTMSI  [0] NULL        OPTIONAL,
    freezeP-TMSI    [1] NULL        OPTIONAL,
    extensionContainer  ExtensionContainer  OPTIONAL,
    ...}

SendIdentificationArg ::= SEQUENCE {
    tmsi            TMSI,
    numberOfRequestedVectors    NumberOfRequestedVectors    OPTIONAL,
    --  within a dialogue numberOfRequestedVectors shall be present in 
    -- the first service request and shall not be present in subsequent service requests. If received
    -- in a subsequent service request it shall be discarded. 
    segmentationProhibited  NULL            OPTIONAL,
    extensionContainer  ExtensionContainer  OPTIONAL,
    ...,
msc-Number	ISDN-AddressString 	OPTIONAL,
	previous-LAI	[0] LAIFixedLength	OPTIONAL,
	hopCounter	[1] HopCounter	OPTIONAL 
}

HopCounter ::= INTEGER (0..3)

SendIdentificationRes ::= [3] SEQUENCE {
    imsi            IMSI            OPTIONAL,
    -- IMSI shall be present in the first (or only) service response of a dialogue.
    -- If multiple service requests are present in a dialogue then IMSI
    -- shall not be present in any service response other than the first one.
    authenticationSetList   AuthenticationSetList   OPTIONAL,
    currentSecurityContext  [2]CurrentSecurityContext   OPTIONAL,
    extensionContainer  [3] ExtensionContainer  OPTIONAL,
    ...}

-- authentication management types

AuthenticationSetList ::= CHOICE {
    tripletList [0] TripletList,
    quintupletList  [1] QuintupletList }

TripletList ::= SEQUENCE SIZE (1..5) OF
                AuthenticationTriplet

QuintupletList ::= SEQUENCE SIZE (1..5) OF
                AuthenticationQuintuplet

AuthenticationTriplet ::= SEQUENCE {
    rand            RAND,
    sres            SRES,
    kc          Kc,
    ...}

AuthenticationQuintuplet ::= SEQUENCE {
    rand            RAND,
    xres            XRES,
    ck          CK,
    ik          IK,
    autn            AUTN,
    ...}

CurrentSecurityContext ::= CHOICE {
    gsm-SecurityContextData [0] GSM-SecurityContextData,
    umts-SecurityContextData    [1] UMTS-SecurityContextData }

GSM-SecurityContextData ::= SEQUENCE {
    kc          Kc,
    cksn            Cksn,
    ... }

UMTS-SecurityContextData ::= SEQUENCE {
    ck          CK,
    ik          IK,
    ksi         KSI,
    ... }

RAND ::= OCTET STRING (SIZE (16))

SRES ::= OCTET STRING (SIZE (4))

Kc ::= OCTET STRING (SIZE (8))

XRES ::= OCTET STRING (SIZE (4..16))

CK ::= OCTET STRING (SIZE (16))

IK ::= OCTET STRING (SIZE (16))

AUTN ::= OCTET STRING (SIZE (16))

AUTS ::= OCTET STRING (SIZE (14))

Cksn ::= OCTET STRING (SIZE (1))
    -- The internal structure is defined in 3G TS 24.008

KSI ::= OCTET STRING (SIZE (1))
    -- The internal structure is defined in 3G TS 24.008

AuthenticationFailureReportArg ::= SEQUENCE {
    imsi            IMSI,
    failureCause    FailureCause,
    extensionContainer  ExtensionContainer  OPTIONAL,
    ... ,
    re-attempt	BOOLEAN		OPTIONAL,
    accessType	AccessType	OPTIONAL,
    rand			RAND			OPTIONAL,
    vlr-Number	[0] ISDN-AddressString	OPTIONAL,
    sgsn-Number	[1] ISDN-AddressString	OPTIONAL }

AccessType ::= ENUMERATED {
    call (0),
    emergencyCall (1),
    locationUpdating (2),
    supplementaryService (3),
    shortMessage (4),
    gprsAttach (5),
    routingAreaUpdating (6),
    serviceRequest (7),
    pdpContextActivation (8),
    pdpContextDeactivation (9),
    ...,
    gprsDetach (10)}
    -- exception handling:
    -- received values greater than 10 shall be ignored.

AuthenticationFailureReportRes ::= SEQUENCE {
    extensionContainer	ExtensionContainer	OPTIONAL,
    ...}

FailureCause ::= ENUMERATED {
    wrongUserResponse  (0),
    wrongNetworkSignature  (1)}

-- gprs location registration types

UpdateGprsLocationArg ::= SEQUENCE {
    imsi            IMSI,
    sgsn-Number ISDN-AddressString, 
    sgsn-Address    GSN-Address,
    extensionContainer  ExtensionContainer  OPTIONAL,
    ... ,
    sgsn-Capability [0] SGSN-Capability OPTIONAL,
    informPreviousNetworkEntity	[1]	NULL		OPTIONAL,
    ps-LCS-NotSupportedByUE	[2]	NULL		OPTIONAL ,
    v-gmlc-Address	[3]	GSN-Address	OPTIONAL,
    add-info		[4]  ADD-Info	OPTIONAL }

SGSN-Capability ::= SEQUENCE{
    solsaSupportIndicator   NULL            OPTIONAL,
    extensionContainer  [1] ExtensionContainer  OPTIONAL,
    ... ,
    superChargerSupportedInServingNetworkEntity [2] SuperChargerInfo  OPTIONAL,
    gprsEnhancementsSupportIndicator    [3] NULL                    OPTIONAL,
    supportedCamelPhases                [4] SupportedCamelPhases    OPTIONAL,
    supportedLCS-CapabilitySets	[5]  SupportedLCS-CapabilitySets    OPTIONAL,
    offeredCamel4CSIs	[6] OfferedCamel4CSIs	                    OPTIONAL ,
    smsCallBarringSupportIndicator	[7]	NULL		OPTIONAL }

GSN-Address ::= OCTET STRING (SIZE (5..17))
    -- Octets are coded according to TS GSM 3GPP TS 23.003 [17]

UpdateGprsLocationRes ::= SEQUENCE {
    hlr-Number  ISDN-AddressString,
    extensionContainer  ExtensionContainer  OPTIONAL,
    ...,
    add-Capability	NULL			OPTIONAL}

-- handover types

ForwardAccessSignalling-Arg ::= [3] SEQUENCE {
    an-APDU     AccessNetworkSignalInfo,
    integrityProtectionInfo [0] IntegrityProtectionInformation      OPTIONAL,
    encryptionInfo  [1] EncryptionInformation       OPTIONAL,
    keyStatus       [2] KeyStatus   OPTIONAL,
    extensionContainer  [3] ExtensionContainer  OPTIONAL,
    ..., 
    allowedGSM-Algorithms       [4]     AllowedGSM-Algorithms   OPTIONAL,
    allowedUMTS-Algorithms      [5]     AllowedUMTS-Algorithms  OPTIONAL,
    radioResourceInformation    [6]     RadioResourceInformation    OPTIONAL,
    radioResourceList           [7]     RadioResourceList     OPTIONAL,
    bssmap-ServiceHandover      [9]     BSSMAP-ServiceHandover	OPTIONAL,
    ranap-ServiceHandover	[8]     RANAP-ServiceHandover    OPTIONAL,
    bssmap-ServiceHandoverList  [10]    BSSMAP-ServiceHandoverList    OPTIONAL,
    currentlyUsedCodec  [11] Codec      OPTIONAL,
    availableCodecsList	[12] AvailableCodecsList        OPTIONAL,
    rab-ConfigurationIndicator [13] NULL       OPTIONAL,
    iuSelectedCodec	[14]	Codec	OPTIONAL,
    alternativeChannelType	[15]	RadioResourceInformation  OPTIONAL 

     }

AllowedGSM-Algorithms ::= OCTET STRING (SIZE (1))
    -- internal structure is coded as Algorithm identifier octet from
    -- Permitted Algorithms defined in 3GPP TS 48.008
    -- A node shall mark all GSM algorithms that are allowed in MSC-B

AllowedUMTS-Algorithms ::= SEQUENCE {
    integrityProtectionAlgorithms   [0]     PermittedIntegrityProtectionAlgorithms    OPTIONAL,
    encryptionAlgorithms    [1]   PermittedEncryptionAlgorithms    OPTIONAL,
    extensionContainer	[2]    ExtensionContainer    OPTIONAL,
    ...}

PermittedIntegrityProtectionAlgorithms ::=
    OCTET STRING (SIZE (1..maxPermittedIntegrityProtectionAlgorithmsLength))
    -- Octets contain a complete PermittedIntegrityProtectionAlgorithms data 
    -- type as defined in 3GPP TS 25.413, encoded according to the encoding 
    -- scheme mandated by 3GPP TS 25.413. 
    -- Padding bits are included, if needed, in the least significant bits of 
    -- the last octet of the octet string. 

maxPermittedIntegrityProtectionAlgorithmsLength INTEGER ::= 9

PermittedEncryptionAlgorithms ::= OCTET STRING (SIZE (1..maxPermittedEncryptionAlgorithmsLength))
    -- Octets contain a complete PermittedEncryptionAlgorithms data type 
    -- as defined in 3GPP TS 25.413, encoded according to the encoding scheme 
    -- mandated by 3GPP TS 25.413
    -- Padding bits are included, if needed, in the least significant bits of 
    -- the last octet of the octet string. 

maxPermittedEncryptionAlgorithmsLength INTEGER ::= 9


KeyStatus ::= ENUMERATED {
    old  (0),
    new  (1),
    ...}
    -- exception handling:
    -- received values in range 2-31 shall be treated as "old"
    -- received values greater than 31 shall be treated as "new"

PrepareHO-Arg ::= [3] SEQUENCE {
    targetCellId    [0] GlobalCellId    OPTIONAL,
    ho-NumberNotRequired    NULL            OPTIONAL, 
    targetRNCId [1] RNCId       OPTIONAL,
    an-APDU     [2] AccessNetworkSignalInfo OPTIONAL,
    multipleBearerRequested [3] NULL        OPTIONAL,
    imsi            [4] IMSI        OPTIONAL,
    integrityProtectionInfo [5] IntegrityProtectionInformation      OPTIONAL,
    encryptionInfo  [6] EncryptionInformation       OPTIONAL,
    radioResourceInformation    [7] RadioResourceInformation    OPTIONAL,
    allowedGSM-Algorithms       [9]  AllowedGSM-Algorithms      OPTIONAL,
    allowedUMTS-Algorithms      [10] AllowedUMTS-Algorithms     OPTIONAL,
    radioResourceList   [11] RadioResourceList	OPTIONAL,
    extensionContainer  [8] ExtensionContainer  OPTIONAL,
    ...,
    rab-Id                      [12] RAB-Id    OPTIONAL,
    bssmap-ServiceHandover      [13]	BSSMAP-ServiceHandover	OPTIONAL,
    ranap-ServiceHandover       [14]	RANAP-ServiceHandover   OPTIONAL, 
    bssmap-ServiceHandoverList [15]    BSSMAP-ServiceHandoverList   OPTIONAL,
    asciCallReference   [20]    ASCI-CallReference   OPTIONAL,
    geran-classmark     [16] GERAN-Classmark   OPTIONAL,
    currentlyUsedCodec	[17] Codec    OPTIONAL,
    availableCodecsList [18] AvailableCodecsList    OPTIONAL,
    rab-ConfigurationIndicator  [19] NULL   OPTIONAL,
    uesbi-Iu		[21]	UESBI-Iu	OPTIONAL ,
    imeisv		[22]	IMEI		OPTIONAL,
    alternativeChannelType	[23]	RadioResourceInformation	OPTIONAL
 }

BSSMAP-ServiceHandoverList ::= SEQUENCE SIZE (1.. maxNumOfServiceHandovers) OF
				BSSMAP-ServiceHandoverInfo

BSSMAP-ServiceHandoverInfo ::= SEQUENCE {
    bssmap-ServiceHandover	BSSMAP-ServiceHandover,
    rab-Id		RAB-Id,
    -- RAB Identity is needed to relate the service handovers with the radio 
    -- access bearers. 
    ...}

maxNumOfServiceHandovers  INTEGER ::= 7

BSSMAP-ServiceHandover ::= OCTET STRING (SIZE (1))
    -- Octets are coded according the Service Handover information element in
    -- 3GPP TS 48.008.

RANAP-ServiceHandover ::= OCTET STRING (SIZE (1))
    -- Octet contains a complete Service-Handover data type 
    -- as defined in 3GPP TS 25.413, encoded according to the encoding scheme 
    -- mandated by 3GPP TS 25.413
    -- Padding bits are included in the least significant bits. 

RadioResourceList ::= SEQUENCE SIZE (1.. maxNumOfRadioResources) OF
				RadioResource

RadioResource ::= SEQUENCE {
    radioResourceInformation	RadioResourceInformation,
    rab-Id		RAB-Id,
    -- RAB Identity is needed to relate the radio resources with the radio 
    -- access bearers. 
    ...}

maxNumOfRadioResources  INTEGER ::= 7


PrepareHO-Res ::= [3] SEQUENCE {
    handoverNumber  [0] ISDN-AddressString  OPTIONAL,
    relocationNumberList    [1] RelocationNumberList    OPTIONAL,
    an-APDU     [2] AccessNetworkSignalInfo OPTIONAL,
    multicallBearerInfo [3] MulticallBearerInfo OPTIONAL,
    multipleBearerNotSupported  NULL            OPTIONAL,
    selectedUMTS-Algorithms     [5]    SelectedUMTS-Algorithms   OPTIONAL,
    chosenRadioResourceInformation     [6] ChosenRadioResourceInformation           OPTIONAL,
    extensionContainer  [4] ExtensionContainer  OPTIONAL,
    ..., 
    iuSelectedCodec    [7] Codec      OPTIONAL ,
    iuAvailableCodecsList	[8] CodecList	OPTIONAL }

SelectedUMTS-Algorithms ::= SEQUENCE {
    integrityProtectionAlgorithm   [0] 	ChosenIntegrityProtectionAlgorithm      OPTIONAL,
    encryptionAlgorithm	[1]    ChosenEncryptionAlgorithm   OPTIONAL,
    extensionContainer  [2]    ExtensionContainer    OPTIONAL,
    ...}

ChosenIntegrityProtectionAlgorithm ::= OCTET STRING (SIZE (1))
    -- Octet contains a complete IntegrityProtectionAlgorithm data type 
    -- as defined in 3GPP TS 25.413, encoded according to the encoding scheme 
    -- mandated by 3GPP TS 25.413
    -- Padding bits are included in the least significant bits. 

ChosenEncryptionAlgorithm ::= OCTET STRING (SIZE (1))
    -- Octet contains a complete EncryptionAlgorithm data type 
    -- as defined in 3GPP TS 25.413, encoded according to the encoding scheme 
    -- mandated by 3GPP TS 25.413
    -- Padding bits are included in the least significant bits. 

ChosenRadioResourceInformation ::= SEQUENCE {
    chosenChannelInfo   [0] ChosenChannelInfo   OPTIONAL,
    chosenSpeechVersion	[1] ChosenSpeechVersion	OPTIONAL,
    ...}

ChosenChannelInfo ::= OCTET STRING (SIZE (1))
    -- Octets are coded according the Chosen Channel information element in 3GPP
    -- TS 48.008

ChosenSpeechVersion ::= OCTET STRING (SIZE (1))
    -- Octets are coded according the Speech Version (chosen) information 
    -- element in 3GPP TS 48.008 


PrepareSubsequentHO-Arg ::= [3] SEQUENCE {
    targetCellId    [0] GlobalCellId    OPTIONAL,
    targetMSC-Number    [1] ISDN-AddressString,
    targetRNCId [2] RNCId       OPTIONAL,
    an-APDU     [3] AccessNetworkSignalInfo OPTIONAL,
    selectedRab-Id  [4] RAB-Id  OPTIONAL,
    extensionContainer  [5] ExtensionContainer  OPTIONAL,
    ..., 
    geran-classmark	[6] GERAN-Classmark	OPTIONAL,
    rab-ConfigurationIndicator	[7] NULL		OPTIONAL }


PrepareSubsequentHO-Res ::= [3] SEQUENCE {
    an-APDU     AccessNetworkSignalInfo,
    extensionContainer  [0] ExtensionContainer  OPTIONAL,
    ...}

ProcessAccessSignalling-Arg ::= [3] SEQUENCE {
    an-APDU     AccessNetworkSignalInfo,
    selectedUMTS-Algorithms     [1]     SelectedUMTS-Algorithms	OPTIONAL,
    selectedGSM-Algorithm       [2]     SelectedGSM-Algorithm   OPTIONAL,
    chosenRadioResourceInformation  [3] ChosenRadioResourceInformation OPTIONAL,
    selectedRab-Id      [4] RAB-Id    OPTIONAL,
    extensionContainer  [0] ExtensionContainer  OPTIONAL,
    ...,
    iUselectedCodec       [5] Codec              OPTIONAL ,
   iuAvailableCodecsList	[6] CodecList	OPTIONAL}

SupportedCodecsList ::= SEQUENCE {
	utranCodecList	[0] CodecList	OPTIONAL,
	geranCodecList	[1] CodecList	OPTIONAL,
	extensionContainer	[2] ExtensionContainer	OPTIONAL,
	...}

AvailableCodecsList ::= SEQUENCE {
    utranCodecList	[0] CodecList	OPTIONAL,
    geranCodecList	[1] CodecList	OPTIONAL,
    extensionContainer	[2] ExtensionContainer	OPTIONAL,
    ...}

CodecList ::= SEQUENCE {
    codec1		[1] Codec,
    codec2		[2] Codec		OPTIONAL,
    codec3		[3] Codec		OPTIONAL,
    codec4		[4] Codec		OPTIONAL,
    codec5		[5] Codec		OPTIONAL,
    codec6		[6] Codec		OPTIONAL,
    codec7		[7] Codec		OPTIONAL,
    codec8		[8] Codec		OPTIONAL,
    extensionContainer	[9] ExtensionContainer	OPTIONAL,
    ...}
    -- Codecs are sent in priority order where codec1 has highest priority

Codec ::= OCTET STRING (SIZE (1..4))

    -- The internal structure is defined as follows:
    -- octet 1	Coded as Codec Identification code in 3GPP TS 26.103
    -- octets 2,3,4	Parameters for the Codec as defined in 3GPP TS
    --			26.103, if available, length depending on the codec

GERAN-Classmark ::= OCTET STRING (SIZE (2..87))
    -- Octets are coded according the GERAN Classmark information element in 
    -- 3GPP TS 48.008

SelectedGSM-Algorithm ::= OCTET STRING (SIZE (1))
    -- internal structure is coded as Algorithm identifier octet from Chosen 
    -- Encryption Algorithm defined in 3GPP TS 48.008
    -- A node shall mark only the selected GSM algorithm

SendEndSignal-Arg ::= [3] SEQUENCE {
    an-APDU     AccessNetworkSignalInfo,
    extensionContainer  [0] ExtensionContainer  OPTIONAL,
    ...}

SendEndSignal-Res ::= SEQUENCE {
    extensionContainer  [0] ExtensionContainer  OPTIONAL,
    ...}

RNCId ::= OCTET STRING (SIZE (7))
    -- The internal structure is defined as follows:
    -- octet 1 bits 4321	Mobile Country Code 1st digit
    --         bits 8765	Mobile Country Code 2nd digit
    -- octet 2 bits 4321	Mobile Country Code 3rd digit
    --         bits 8765	Mobile Network Code 3rd digit
    --			or filler (1111) for 2 digit MNCs
    -- octet 3 bits 4321	Mobile Network Code 1st digit
    --         bits 8765	Mobile Network Code 2nd digit
    -- octets 4 and 5	Location Area Code according to 3GPP TS 24.008
    -- octets 6 and 7	RNC Id value according to 3GPP TS 25.413

RelocationNumberList ::= SEQUENCE SIZE (1..maxNumOfRelocationNumber) OF
                RelocationNumber

MulticallBearerInfo ::= INTEGER (1..maxNumOfRelocationNumber)

RelocationNumber ::= SEQUENCE {
    handoverNumber  ISDN-AddressString,
    rab-Id      RAB-Id,
    -- RAB Identity is needed to relate the calls with the radio access bearers. 
    ...}

RAB-Id ::= INTEGER (1..maxNrOfRABs)

maxNrOfRABs INTEGER ::= 255

maxNumOfRelocationNumber  INTEGER ::= 7

RadioResourceInformation ::= OCTET STRING (SIZE (3..13))
    -- Octets are coded according the Channel Type information element in 3GPP TS 48.008


IntegrityProtectionInformation ::= OCTET STRING (SIZE (18..maxNumOfIntegrityInfo))
    -- Octets contain a complete IntegrityProtectionInformation data type 
    -- as defined in 3GPP TS 25.413, encoded according to the encoding scheme 
    -- mandated by 3GPP TS 25.413
    -- Padding bits are included, if needed, in the least significant bits of 
    -- the last octet of the octet string.



maxNumOfIntegrityInfo INTEGER ::= 100

EncryptionInformation ::= OCTET STRING (SIZE (18..maxNumOfEncryptionInfo))
    -- Octets contain a complete EncryptionInformation data type 
    -- as defined in 3GPP TS 25.413, encoded according to the encoding scheme 
    -- mandated by 3GPP TS 25.413
    -- Padding bits are included, if needed, in the least significant bits of 
    -- the last octet of the octet string. 


maxNumOfEncryptionInfo INTEGER ::= 100

-- authentication management types

SendAuthenticationInfoArg ::= SEQUENCE {
    imsi            [0] IMSI,
    numberOfRequestedVectors    NumberOfRequestedVectors,
    segmentationProhibited  NULL            OPTIONAL,
    immediateResponsePreferred  [1] NULL            OPTIONAL,
    re-synchronisationInfo  Re-synchronisationInfo  OPTIONAL,
    extensionContainer  [2] ExtensionContainer  OPTIONAL,
    ...,
    requestingNodeType	[3] RequestingNodeType	OPTIONAL,
    requestingPLMN-Id	[4] PLMN-Id	OPTIONAL  }

PLMN-Id ::= OCTET STRING (SIZE (3))    

NumberOfRequestedVectors ::= INTEGER (1..5)

Re-synchronisationInfo ::= SEQUENCE {
    rand            RAND,
    auts            AUTS,
    ...}

SendAuthenticationInfoRes ::= [3] SEQUENCE {
    authenticationSetList   AuthenticationSetList   OPTIONAL,
    extensionContainer  ExtensionContainer  OPTIONAL,
    ...}

RequestingNodeType ::= ENUMERATED {
    vlr  (0),
    sgsn  (1),
    ...}
    -- exception handling:
    -- received values in the range 2-15 shall be treated as "vlr"
    -- received values greater than 15 shall be treated as "sgsn"

-- equipment management types

CheckIMEI-Arg ::= SEQUENCE {
    imei			IMEI,
    requestedEquipmentInfo	RequestedEquipmentInfo,
    extensionContainer	ExtensionContainer	OPTIONAL,
    ...}

CheckIMEI-Res ::= SEQUENCE {
    equipmentStatus	EquipmentStatus	OPTIONAL,
    bmuef		UESBI-Iu		OPTIONAL,
    extensionContainer	ExtensionContainer	OPTIONAL,
    ...}

RequestedEquipmentInfo::= BIT STRING {
    equipmentStatus  (0),
    bmuef  (1)} (SIZE (2..8))
    -- exception handling: reception of unknown bit assignments in the
    -- RequestedEquipmentInfo data type shall be discarded by the receiver 

--UESBI ::= OCTET STRING (SIZE (10))
    -- Octets are coded according the UESBI information element in 3GPP TS 
    -- 25.413.
UESBI-Iu ::= SEQUENCE {
	uesbi-IuA	[0] UESBI-IuA				OPTIONAL,
	uesbi-IuB	[1] UESBI-IuB				OPTIONAL,
	...}

UESBI-IuA				::= BIT STRING (SIZE(1..128))
-- See 3GPP TS 25.413
UESBI-IuB				::= BIT STRING (SIZE(1..128))
-- See 3GPP TS 25.413

EquipmentStatus ::= ENUMERATED {
    whiteListed  (0),
    blackListed  (1),
    greyListed  (2)}


-- subscriber management types

InsertSubscriberDataArg ::= SEQUENCE {
    imsi            [0] IMSI        OPTIONAL,
    COMPONENTS OF   SubscriberData,
    extensionContainer  [14] ExtensionContainer OPTIONAL,
    ... ,   
    naea-PreferredCI    [15] NAEA-PreferredCI   OPTIONAL,
    -- naea-PreferredCI is included at the discretion of the HLR operator.
    gprsSubscriptionData    [16] GPRSSubscriptionData   OPTIONAL,
    roamingRestrictedInSgsnDueToUnsupportedFeature [23]     NULL    
                            OPTIONAL, 
    networkAccessMode   [24] NetworkAccessMode  OPTIONAL,
    lsaInformation  [25] LSAInformation OPTIONAL,
    lmu-Indicator   [21]    NULL        OPTIONAL,
    lcsInformation  [22]    LCSInformation  OPTIONAL,
        istAlertTimer   [26] IST-AlertTimerValue    OPTIONAL,
        superChargerSupportedInHLR  [27] AgeIndicator   OPTIONAL,
        mc-SS-Info  [28] MC-SS-Info OPTIONAL,
    cs-AllocationRetentionPriority  [29] CS-AllocationRetentionPriority     OPTIONAL,
    sgsn-CAMEL-SubscriptionInfo [17] SGSN-CAMEL-SubscriptionInfo    OPTIONAL,
    chargingCharacteristics     [18]    ChargingCharacteristics     OPTIONAL,
    accessRestrictionData	[19] AccessRestrictionData	OPTIONAL 
 }
    -- If the Network Access Mode parameter is sent, it shall be present only in 
    -- the first sequence if seqmentation is used

AccessRestrictionData ::= BIT STRING {
	utranNotAllowed (0),
	geranNotAllowed (1) } (SIZE (2..8))
	-- exception handling:
	-- bits 2 to 7 shall be ignored if received and not understood

CS-AllocationRetentionPriority ::= OCTET STRING (SIZE (1))
    -- This data type encodes each priority level defined in TS 23.107 as the binary value
    -- of the priority level.

IST-AlertTimerValue ::= INTEGER (15..255)

LCSInformation ::= SEQUENCE {
    gmlc-List   [0] GMLC-List   OPTIONAL,
    lcs-PrivacyExceptionList    [1] LCS-PrivacyExceptionList    OPTIONAL,
    molr-List       [2] MOLR-List   OPTIONAL,
    ...,
    add-lcs-PrivacyExceptionList	[3]	LCS-PrivacyExceptionList OPTIONAL }
    -- add-lcs-PrivacyExceptionList may be sent only if lcs-PrivacyExceptionList 
    -- is present and contains four instances of LCS-PrivacyClass. If the 
    -- mentioned condition is not satisfied the receiving node shall discard 
    -- add-lcs-PrivacyExceptionList.
    -- If an LCS-PrivacyClass is received both in lcs-PrivacyExceptionList and 
    -- in add-lcs-PrivacyExceptionList with the same SS-Code, then the error 
    -- unexpected data value shall be returned.


GMLC-List ::= SEQUENCE SIZE (1..maxNumOfGMLC) OF
                ISDN-AddressString
    -- if segmentation is used, the complete GMLC-List shall be sent in one segment

maxNumOfGMLC  INTEGER ::= 5


NetworkAccessMode ::= ENUMERATED {
    bothMSCAndSGSN  (0),
    onlyMSC     (1),
    onlySGSN        (2),
    ...}
    -- if unknown values are received in NetworkAccessMode
    -- they shall be discarded.

GPRSDataList ::= SEQUENCE SIZE (1..maxNumOfPDP-Contexts) OF
                PDP-Context

maxNumOfPDP-Contexts  INTEGER ::= 50

PDP-Context ::= SEQUENCE {
    pdp-ContextId   ContextId,
    pdp-Type        [16] PDP-Type,
    pdp-Address [17] PDP-Address    OPTIONAL,
    qos-Subscribed  [18] QoS-Subscribed,
    vplmnAddressAllowed [19] NULL   OPTIONAL,
    apn         [20] APN,
    extensionContainer  [21] ExtensionContainer OPTIONAL,
    ... ,
    ext-QoS-Subscribed  [0] Ext-QoS-Subscribed  OPTIONAL, 
    pdp-ChargingCharacteristics [1] ChargingCharacteristics OPTIONAL,
    ext2-QoS-Subscribed	[2] Ext2-QoS-Subscribed	OPTIONAL
    -- ext2-QoS-Subscribed may be present only if ext-QoS-Subscribed is present.
 }
    

ContextId ::= INTEGER (1..maxNumOfPDP-Contexts)

GPRSSubscriptionData ::= SEQUENCE {
    completeDataListIncluded    NULL            OPTIONAL,

        -- If segmentation is used, completeDataListIncluded may only be present in the
        -- first segment.
    gprsDataList    [1] GPRSDataList,
    extensionContainer  [2] ExtensionContainer  OPTIONAL,
    ... }

SGSN-CAMEL-SubscriptionInfo ::= SEQUENCE {
    gprs-CSI        [0] GPRS-CSI    OPTIONAL,
    mo-sms-CSI     [1] SMS-CSI OPTIONAL,
    extensionContainer  [2] ExtensionContainer  OPTIONAL,
    ...,
    mt-sms-CSI	[3]	SMS-CSI	OPTIONAL,
    mt-smsCAMELTDP-CriteriaList	[4]	MT-smsCAMELTDP-CriteriaList	OPTIONAL,
    mg-csi		[5]	MG-CSI	OPTIONAL }

GPRS-CSI ::= SEQUENCE {
    gprs-CamelTDPDataList   [0] GPRS-CamelTDPDataList   OPTIONAL,
    camelCapabilityHandling [1] CamelCapabilityHandling OPTIONAL,
    extensionContainer  [2] ExtensionContainer  OPTIONAL,
    notificationToCSE   [3] NULL        OPTIONAL,
    csi-Active  [4] NULL        OPTIONAL,
    ...}
--  notificationToCSE and csi-Active shall not be present when GPRS-CSI is sent to SGSN.
--  They may only be included in ATSI/ATM ack/NSDC message. 
--  GPRS-CamelTDPData and  camelCapabilityHandling shall be present in 
--  the GPRS-CSI sequence.
--  If GPRS-CSI is segmented, gprs-CamelTDPDataList and camelCapabilityHandling shall be 
--  present in the first segment

GPRS-CamelTDPDataList ::= SEQUENCE SIZE (1..maxNumOfCamelTDPData) OF
    GPRS-CamelTDPData
--  GPRS-CamelTDPDataList shall not contain more than one instance of
--  GPRS-CamelTDPData containing the same value for gprs-TriggerDetectionPoint.

GPRS-CamelTDPData ::= SEQUENCE {
    gprs-TriggerDetectionPoint  [0] GPRS-TriggerDetectionPoint,
    serviceKey  [1] ServiceKey,
    gsmSCF-Address  [2] ISDN-AddressString,
    defaultSessionHandling  [3] DefaultGPRS-Handling,
    extensionContainer  [4] ExtensionContainer  OPTIONAL,
    ...
    }

DefaultGPRS-Handling ::= ENUMERATED {
    continueTransaction (0) ,
    releaseTransaction (1) ,
    ...}
-- exception handling:
-- reception of values in range 2-31 shall be treated as "continueTransaction"
-- reception of values greater than 31 shall be treated as "releaseTransaction"

GPRS-TriggerDetectionPoint ::= ENUMERATED {
    attach          (1),
    attachChangeOfPosition      (2),
    pdp-ContextEstablishment        (11),
    pdp-ContextEstablishmentAcknowledgement (12),
    pdp-ContextChangeOfPosition         (14),
    ... }
-- exception handling:
-- For GPRS-CamelTDPData sequences containing this parameter with any
-- other value than the ones listed the receiver shall ignore the whole 
-- GPRS-CamelTDPDatasequence.

APN ::=  OCTET STRING (SIZE (2..63))
    -- Octets are coded according to TS 3GPP TS 23.003 [17] 

PDP-Type ::= OCTET STRING (SIZE (2))
    -- Octets are coded according to TS 3GPP TS 29.060 [105]

PDP-Address ::= OCTET STRING (SIZE (1..16))
    -- Octets are coded according to TS 3GPP TS 29.060 [105]

    -- The possible size values are:
    -- 1-7 octets  X.25 address type
    --  4  octets  IPv4 address type
    -- 16  octets  Ipv6 address type

QoS-Subscribed ::= OCTET STRING (SIZE (3))
    -- Octets are coded according to TS 3GPP TS 24.008 [35] Quality of Service Octets 3-5 .

Ext-QoS-Subscribed ::= OCTET STRING (SIZE (1..9))
    -- OCTET 1: 
    --  Allocation/Retention Priority (This octet encodes each priority level defined in
    --     23.107 as the binary value of the priority level, declaration in 29.060)
    -- Octets 2-9 are coded according to 3G TS 24.008[35] Quality of Service Octets 
    -- 6-13.
Ext2-QoS-Subscribed ::= OCTET STRING (SIZE (1..3))
-- Octets 1-3 are coded according to 3GPP TS 24.008 [35] Quality of Service Octets 14-16.
-- If Quality of Service information is structured with 14 octet length, then
-- Octet 1 is coded according to 3GPP TS 24.008 [35] Quality of Service Octet 14

ChargingCharacteristics ::= OCTET STRING (SIZE (2))
-- Octets are coded according to 3G TS 32.015.

LSAOnlyAccessIndicator ::= ENUMERATED {
    accessOutsideLSAsAllowed  (0),
    accessOutsideLSAsRestricted (1)}

LSADataList ::= SEQUENCE SIZE (1..maxNumOfLSAs) OF
                LSAData

maxNumOfLSAs  INTEGER ::= 20

LSAData ::= SEQUENCE {
    lsaIdentity [0] LSAIdentity,
    lsaAttributes   [1] LSAAttributes,
    lsaActiveModeIndicator  [2] NULL        OPTIONAL,
    extensionContainer  [3] ExtensionContainer  OPTIONAL,
    ...}

LSAInformation ::= SEQUENCE {
    completeDataListIncluded    NULL            OPTIONAL,

        -- If segmentation is used, completeDataListIncluded may only be present in the
        -- first segment.
    lsaOnlyAccessIndicator  [1] LSAOnlyAccessIndicator  OPTIONAL,
    lsaDataList [2] LSADataList OPTIONAL,
    extensionContainer  [3] ExtensionContainer  OPTIONAL,
    ...}

LSAIdentity ::= OCTET STRING (SIZE (3))
    -- Octets are coded according to TS 3GPP TS 23.003 [17]

LSAAttributes ::= OCTET STRING (SIZE (1))
    -- Octets are coded according to TS 3GPP TS 48.008 [49]


SubscriberData ::= SEQUENCE {
    msisdn      [1] ISDN-AddressString  OPTIONAL,
    category        [2] Category    OPTIONAL,
    subscriberStatus    [3] SubscriberStatus    OPTIONAL,
    bearerServiceList   [4] BearerServiceList   OPTIONAL,
    -- The exception handling for reception of unsupported / not allocated
    -- bearerServiceCodes is defined in section 8.8.1
    teleserviceList [6] TeleserviceList OPTIONAL,
    -- The exception handling for reception of unsupported / not allocated
    -- teleserviceCodes is defined in section 8.8.1
    provisionedSS   [7] Ext-SS-InfoList OPTIONAL,
    odb-Data        [8] ODB-Data    OPTIONAL,
    roamingRestrictionDueToUnsupportedFeature  [9] NULL OPTIONAL,
    regionalSubscriptionData    [10] ZoneCodeList   OPTIONAL,
    vbsSubscriptionData [11] VBSDataList    OPTIONAL,
    vgcsSubscriptionData    [12] VGCSDataList   OPTIONAL,
    vlrCamelSubscriptionInfo    [13] VlrCamelSubscriptionInfo   OPTIONAL
    }

Category ::= OCTET STRING (SIZE (1))
    -- The internal structure is defined in CCITT Rec Q.763.

SubscriberStatus ::= ENUMERATED {
    serviceGranted  (0),
    operatorDeterminedBarring  (1)}

BearerServiceList ::= SEQUENCE SIZE (1..maxNumOfBearerServices) OF
                Ext-BearerServiceCode

maxNumOfBearerServices  INTEGER ::= 50

TeleserviceList ::= SEQUENCE SIZE (1..maxNumOfTeleservices) OF
                Ext-TeleserviceCode

maxNumOfTeleservices  INTEGER ::= 20

ODB-Data ::= SEQUENCE {
    odb-GeneralData ODB-GeneralData,
    odb-HPLMN-Data  ODB-HPLMN-Data  OPTIONAL,
    extensionContainer  ExtensionContainer  OPTIONAL,
    ...}

ODB-GeneralData ::= BIT STRING {
    allOG-CallsBarred  (0),
    internationalOGCallsBarred  (1),
    internationalOGCallsNotToHPLMN-CountryBarred  (2),
    interzonalOGCallsBarred (6),
    interzonalOGCallsNotToHPLMN-CountryBarred (7),
    interzonalOGCallsAndInternationalOGCallsNotToHPLMN-CountryBarred (8),
    premiumRateInformationOGCallsBarred  (3),
    premiumRateEntertainementOGCallsBarred  (4),
    ss-AccessBarred  (5),
    allECT-Barred (9),
    chargeableECT-Barred (10),
    internationalECT-Barred (11),
    interzonalECT-Barred (12),
    doublyChargeableECT-Barred (13),
    multipleECT-Barred (14),
    allPacketOrientedServicesBarred (15),
    roamerAccessToHPLMN-AP-Barred  (16),
    roamerAccessToVPLMN-AP-Barred  (17),
    roamingOutsidePLMNOG-CallsBarred  (18),
    allIC-CallsBarred  (19),
    roamingOutsidePLMNIC-CallsBarred  (20),
    roamingOutsidePLMNICountryIC-CallsBarred  (21),
    roamingOutsidePLMN-Barred  (22),
    roamingOutsidePLMN-CountryBarred  (23),
    registrationAllCF-Barred  (24),
    registrationCFNotToHPLMN-Barred  (25),
    registrationInterzonalCF-Barred  (26),
    registrationInterzonalCFNotToHPLMN-Barred  (27),
    registrationInternationalCF-Barred  (28)} (SIZE (15..32))
    -- exception handling: reception of unknown bit assignments in the
    -- ODB-GeneralData type shall be treated like unsupported ODB-GeneralData
    -- When the ODB-GeneralData type is removed from the HLR for a given 
    -- subscriber, in NoteSubscriberDataModified operation sent toward the 
    -- gsmSCF all bits shall be set to "O".


ODB-HPLMN-Data ::= BIT STRING {
    plmn-SpecificBarringType1  (0),
    plmn-SpecificBarringType2  (1),
    plmn-SpecificBarringType3  (2),
    plmn-SpecificBarringType4  (3)} (SIZE (4..32))
    -- exception handling: reception of unknown bit assignments in the
    -- ODB-HPLMN-Data type shall be treated like unsupported ODB-HPLMN-Data 
    -- When the ODB-HPLMN-Data type is removed from the HLR for a given 
    -- subscriber, in NoteSubscriberDataModified operation sent toward the 
    -- gsmSCF all bits shall be set to "O".


Ext-SS-InfoList ::= SEQUENCE SIZE (1..maxNumOfSS) OF
                Ext-SS-Info

Ext-SS-Info ::= CHOICE {
    forwardingInfo  [0] Ext-ForwInfo,
    callBarringInfo [1] Ext-CallBarInfo,
    cug-Info        [2] CUG-Info,
    ss-Data     [3] Ext-SS-Data,
    emlpp-Info  [4] EMLPP-Info}


Ext-ForwInfo ::= SEQUENCE {
    ss-Code     SS-Code,
    forwardingFeatureList   Ext-ForwFeatureList,
    extensionContainer  [0] ExtensionContainer  OPTIONAL,
    ...}

Ext-ForwFeatureList ::= SEQUENCE SIZE (1..maxNumOfExt-BasicServiceGroups) OF
                Ext-ForwFeature

Ext-ForwFeature ::= SEQUENCE {
    basicService    Ext-BasicServiceCode    OPTIONAL,
    ss-Status       [4] Ext-SS-Status,
    forwardedToNumber   [5] ISDN-AddressString  OPTIONAL,
    -- When this data type is sent from an HLR which supports CAMEL Phase 2
    -- to a VLR that supports CAMEL Phase 2 the VLR shall not check the
    -- format of the number
    forwardedToSubaddress   [8] ISDN-SubaddressString   OPTIONAL,
    forwardingOptions   [6] Ext-ForwOptions OPTIONAL,
    noReplyConditionTime    [7] Ext-NoRepCondTime   OPTIONAL,
    extensionContainer  [9] ExtensionContainer  OPTIONAL,
    ...,
    longForwardedToNumber   [10] FTN-AddressString  OPTIONAL }

Ext-ForwOptions ::= OCTET STRING (SIZE (1..5))

    -- OCTET 1:

    --  bit 8: notification to forwarding party
    --  0  no notification
    --  1  notification

    --  bit 7: redirecting presentation
    --  0 no presentation  
    --  1  presentation

    --  bit 6: notification to calling party
    --  0  no notification
    --  1  notification

    --  bit 5: 0 (unused)

    --  bits 43: forwarding reason
    --  00  ms not reachable
    --  01  ms busy
    --  10  no reply
    --  11  unconditional

    -- bits 21: 00 (unused)

    -- OCTETS 2-5: reserved for future use. They shall be discarded if
    -- received and not understood.

Ext-NoRepCondTime ::= INTEGER (1..100)
    -- Only values 5-30 are used.
    -- Values in the ranges 1-4 and 31-100 are reserved for future use
    -- If received:
    --      values 1-4 shall be mapped on to value 5
    --      values 31-100 shall be mapped on to value 30

Ext-CallBarInfo ::= SEQUENCE {
    ss-Code     SS-Code,
    callBarringFeatureList  Ext-CallBarFeatureList,
    extensionContainer  ExtensionContainer  OPTIONAL,
    ...}

Ext-CallBarFeatureList ::= SEQUENCE SIZE (1..maxNumOfExt-BasicServiceGroups) OF
                Ext-CallBarringFeature

Ext-CallBarringFeature ::= SEQUENCE {
    basicService    Ext-BasicServiceCode    OPTIONAL,
    ss-Status       [4] Ext-SS-Status,
    extensionContainer  ExtensionContainer  OPTIONAL,
    ...}

CUG-Info ::= SEQUENCE {
    cug-SubscriptionList    CUG-SubscriptionList,
    cug-FeatureList CUG-FeatureList OPTIONAL,
    extensionContainer  [0] ExtensionContainer  OPTIONAL,
    ...}

CUG-SubscriptionList ::= SEQUENCE SIZE (0..maxNumOfCUG) OF
                CUG-Subscription

CUG-Subscription ::= SEQUENCE {
    cug-Index   CUG-Index,
    cug-Interlock   CUG-Interlock,
    intraCUG-Options    IntraCUG-Options,
    basicServiceGroupList   Ext-BasicServiceGroupList   OPTIONAL,
    extensionContainer  [0] ExtensionContainer  OPTIONAL,
    ...}

CUG-Index ::= INTEGER (0..32767)
    -- The internal structure is defined in ETS 300 138.

CUG-Interlock ::= OCTET STRING (SIZE (4))

IntraCUG-Options ::= ENUMERATED {
    noCUG-Restrictions  (0),
    cugIC-CallBarred  (1),
    cugOG-CallBarred  (2)}

maxNumOfCUG  INTEGER ::= 10

CUG-FeatureList ::= SEQUENCE SIZE (1..maxNumOfExt-BasicServiceGroups) OF
                CUG-Feature

Ext-BasicServiceGroupList ::= SEQUENCE SIZE (1..maxNumOfExt-BasicServiceGroups) OF
                Ext-BasicServiceCode

maxNumOfExt-BasicServiceGroups  INTEGER ::= 32

CUG-Feature ::= SEQUENCE {
    basicService    Ext-BasicServiceCode    OPTIONAL,
    preferentialCUG-Indicator   CUG-Index   OPTIONAL,
    interCUG-Restrictions   InterCUG-Restrictions,
    extensionContainer  ExtensionContainer  OPTIONAL,
    ...}

InterCUG-Restrictions ::= OCTET STRING (SIZE (1))

    -- bits 876543: 000000 (unused)
    -- Exception handling:
    -- bits 876543 shall be ignored if received and not understood

    -- bits 21
    --  00  CUG only facilities
    --  01  CUG with outgoing access
    --  10  CUG with incoming access
    --  11  CUG with both outgoing and incoming access

Ext-SS-Data ::= SEQUENCE {
    ss-Code     SS-Code,
    ss-Status   [4] Ext-SS-Status,
    ss-SubscriptionOption   SS-SubscriptionOption   OPTIONAL,
    basicServiceGroupList   Ext-BasicServiceGroupList   OPTIONAL,
    extensionContainer  [5] ExtensionContainer  OPTIONAL,
    ...}

LCS-PrivacyExceptionList ::= SEQUENCE SIZE (1..maxNumOfPrivacyClass) OF
                LCS-PrivacyClass

maxNumOfPrivacyClass  INTEGER ::= 4

LCS-PrivacyClass ::= SEQUENCE {
    ss-Code     SS-Code,
    ss-Status       Ext-SS-Status,
    notificationToMSUser    [0] NotificationToMSUser    OPTIONAL,
    -- notificationToMSUser may be sent only for SS-codes callSessionRelated
    -- and callSessionUnrelated. If not received for SS-codes callSessionRelated
    -- and callSessionUnrelated,
    -- the default values according to 3GPP TS 23.271 shall be assumed.
    externalClientList  [1] ExternalClientList  OPTIONAL,
    -- externalClientList may be sent only for SS-code callSessionUnrelated to a
    -- visited node that does not support LCS Release 4 or later versions.
    -- externalClientList may be sent only for SS-codes callSessionUnrelated and
    -- callSessionRelated to a visited node that supports LCS Release 4 or later 
    -- versions.
    plmnClientList  [2] PLMNClientList  OPTIONAL,
    -- plmnClientList may be sent only for SS-code plmnoperator.
    extensionContainer  [3] ExtensionContainer  OPTIONAL,
    ...,
    ext-externalClientList	[4] Ext-ExternalClientList	OPTIONAL,
    -- Ext-externalClientList may be sent only if the visited node supports LCS 
    -- Release 4 or later versions, the user did specify more than 5 clients, 
    -- and White Book SCCP is used.
    serviceTypeList	[5]	ServiceTypeList	OPTIONAL }
    -- serviceTypeList may be sent only for SS-code serviceType and if the 
    -- visited node supports LCS Release 5 or later versions.
    -- 
    -- if segmentation is used, the complete LCS-PrivacyClass shall be sent in 
    -- one segment 

ExternalClientList ::= SEQUENCE SIZE (0..maxNumOfExternalClient) OF
                ExternalClient

maxNumOfExternalClient  INTEGER ::= 5

PLMNClientList ::= SEQUENCE SIZE (1..maxNumOfPLMNClient) OF
                LCSClientInternalID

maxNumOfPLMNClient  INTEGER ::= 5

Ext-ExternalClientList ::= SEQUENCE SIZE (1..maxNumOfExt-ExternalClient) OF
				ExternalClient

maxNumOfExt-ExternalClient  INTEGER ::= 35

ExternalClient ::= SEQUENCE {
    clientIdentity  LCSClientExternalID,
    gmlc-Restriction    [0] GMLC-Restriction    OPTIONAL,
    notificationToMSUser    [1] NotificationToMSUser    OPTIONAL,
    -- If notificationToMSUser is not received, the default value according to 
    -- 3GPP TS 23.271 shall be assumed.
    extensionContainer  [2] ExtensionContainer  OPTIONAL,
    ... }

GMLC-Restriction ::= ENUMERATED {
    gmlc-List       (0),
    home-Country    (1) ,
    ... }
-- exception handling:
-- At reception of any other value than the ones listed the receiver shall ignore
-- GMLC-Restriction.

NotificationToMSUser ::= ENUMERATED {
    notifyLocationAllowed   (0),
    notifyAndVerify-LocationAllowedIfNoResponse (1),
    notifyAndVerify-LocationNotAllowedIfNoResponse  (2),
    ...,
    locationNotAllowed (3)  }
-- exception handling:
-- At reception of any other value than the ones listed the receiver shall ignore
-- NotificationToMSUser.

ServiceTypeList ::= SEQUENCE SIZE (1..maxNumOfServiceType) OF
				ServiceType

maxNumOfServiceType  INTEGER ::= 32

ServiceType ::= SEQUENCE {
    serviceTypeIdentity	LCSServiceTypeID,
    gmlc-Restriction	[0] GMLC-Restriction	OPTIONAL,
    notificationToMSUser	[1] NotificationToMSUser	OPTIONAL,
    -- If notificationToMSUser is not received, the default value according to 
    -- 3GPP TS 23.271 shall be assumed.
    extensionContainer	[2] ExtensionContainer	OPTIONAL,
    ... }


MOLR-List ::= SEQUENCE SIZE (1..maxNumOfMOLR-Class) OF
                MOLR-Class

maxNumOfMOLR-Class  INTEGER ::= 3

MOLR-Class ::= SEQUENCE {
    ss-Code     SS-Code,
    ss-Status       Ext-SS-Status,
    extensionContainer  [0] ExtensionContainer  OPTIONAL,
    ...}

ZoneCodeList ::= SEQUENCE SIZE (1..maxNumOfZoneCodes)
                OF ZoneCode

ZoneCode ::= OCTET STRING (SIZE (2))
    -- internal structure is defined in TS 3GPP TS 23.003 [17]

maxNumOfZoneCodes  INTEGER ::= 10

InsertSubscriberDataRes ::= SEQUENCE {
    teleserviceList [1] TeleserviceList OPTIONAL,
    bearerServiceList   [2] BearerServiceList   OPTIONAL,
    ss-List     [3] SS-List OPTIONAL,
    odb-GeneralData [4] ODB-GeneralData OPTIONAL,
    regionalSubscriptionResponse    [5] RegionalSubscriptionResponse        OPTIONAL,
    supportedCamelPhases    [6] SupportedCamelPhases    OPTIONAL,
    extensionContainer  [7] ExtensionContainer  OPTIONAL,
    ...,
    offeredCamel4CSIs	[8] OfferedCamel4CSIs	OPTIONAL }

RegionalSubscriptionResponse ::= ENUMERATED {
    networkNode-AreaRestricted  (0),
    tooManyZoneCodes    (1),
    zoneCodesConflict   (2),
    regionalSubscNotSupported   (3)}

DeleteSubscriberDataArg ::= SEQUENCE {
    imsi            [0] IMSI,
    basicServiceList    [1] BasicServiceList    OPTIONAL,
    -- The exception handling for reception of unsupported/not allocated
    -- basicServiceCodes is defined in section 6.8.2
    ss-List     [2] SS-List OPTIONAL,
    roamingRestrictionDueToUnsupportedFeature [4] NULL  OPTIONAL,
    regionalSubscriptionIdentifier  [5] ZoneCode    OPTIONAL,
    vbsGroupIndication  [7] NULL        OPTIONAL,
    vgcsGroupIndication [8] NULL     OPTIONAL,
    camelSubscriptionInfoWithdraw   [9] NULL     OPTIONAL,
    extensionContainer  [6] ExtensionContainer OPTIONAL,
    ...,
    gprsSubscriptionDataWithdraw    [10] GPRSSubscriptionDataWithdraw   OPTIONAL,
    roamingRestrictedInSgsnDueToUnsuppportedFeature [11] NULL   OPTIONAL,
    lsaInformationWithdraw  [12] LSAInformationWithdraw OPTIONAL,
    gmlc-ListWithdraw   [13]    NULL        OPTIONAL,
    istInformationWithdraw  [14] NULL       OPTIONAL,
    specificCSI-Withdraw    [15] SpecificCSI-Withdraw   OPTIONAL,
    chargingCharacteristicsWithdraw	[16] NULL		OPTIONAL }

SpecificCSI-Withdraw ::= BIT STRING {
    o-csi (0),
    ss-csi (1),
    tif-csi (2),
    d-csi (3),
    vt-csi (4),
    mo-sms-csi (5),
    m-csi (6),
    gprs-csi(7),
    t-csi (8),
    mt-sms-csi (9),
    mg-csi (10),
    o-IM-CSI (11), 
    d-IM-CSI (12),
    vt-IM-CSI (13)} (SIZE(8..32)) 
-- exception handling:
-- bits 11 to 31 shall be ignored if received by a non-IP Multimedia Core
-- Network entity.
-- bits 0-10 and 14-31 shall be ignored if received by an IP Multimedia Core 
-- Network entity.
-- bits 11-13 are only applicable in an IP Multimedia Core Network.
-- Bit 8 and bits 11-13 are only applicable for the NoteSubscriberDataModified 
-- operation.


GPRSSubscriptionDataWithdraw ::= CHOICE {
    allGPRSData NULL,
    contextIdList   ContextIdList}

ContextIdList ::= SEQUENCE SIZE (1..maxNumOfPDP-Contexts) OF
                ContextId

LSAInformationWithdraw ::= CHOICE {
    allLSAData  NULL,
    lsaIdentityList LSAIdentityList }

LSAIdentityList ::= SEQUENCE SIZE (1..maxNumOfLSAs) OF
                LSAIdentity

BasicServiceList ::= SEQUENCE SIZE (1..maxNumOfBasicServices) OF
                Ext-BasicServiceCode

maxNumOfBasicServices  INTEGER ::= 70

DeleteSubscriberDataRes ::= SEQUENCE {
    regionalSubscriptionResponse    [0] RegionalSubscriptionResponse    OPTIONAL,
    extensionContainer  ExtensionContainer  OPTIONAL,
    ...}

VlrCamelSubscriptionInfo ::= SEQUENCE {
    o-CSI       [0] O-CSI       OPTIONAL,
    extensionContainer  [1] ExtensionContainer  OPTIONAL,
    ...,
    ss-CSI      [2] SS-CSI  OPTIONAL,
    o-BcsmCamelTDP-CriteriaList [4] O-BcsmCamelTDPCriteriaList  OPTIONAL,
    tif-CSI     [3] NULL    OPTIONAL,
    m-CSI       [5] M-CSI   OPTIONAL,
    mo-sms-CSI     [6] SMS-CSI OPTIONAL,
    vt-CSI      [7] T-CSI   OPTIONAL,
    t-BCSM-CAMEL-TDP-CriteriaList   [8] T-BCSM-CAMEL-TDP-CriteriaList   OPTIONAL,
    d-CSI       [9] D-CSI   OPTIONAL,
    mt-sms-CSI	[10] SMS-CSI	OPTIONAL,
    mt-smsCAMELTDP-CriteriaList	[11]	MT-smsCAMELTDP-CriteriaList OPTIONAL }

MT-smsCAMELTDP-CriteriaList ::= SEQUENCE SIZE (1.. maxNumOfCamelTDPData) OF
	MT-smsCAMELTDP-Criteria

MT-smsCAMELTDP-Criteria ::= SEQUENCE {
    sms-TriggerDetectionPoint	SMS-TriggerDetectionPoint,
    tpdu-TypeCriterion	[0]	TPDU-TypeCriterion		OPTIONAL,
    ... }

TPDU-TypeCriterion ::= SEQUENCE SIZE (1..maxNumOfTPDUTypes) OF
	MT-SMS-TPDU-Type

maxNumOfTPDUTypes INTEGER ::= 5

MT-SMS-TPDU-Type ::= ENUMERATED {
    sms-DELIVER 	(0),
    sms-SUBMIT-REPORT 	(1),
    sms-STATUS-REPORT 	(2),
    ... }

--  exception handling:
--  For TPDU-TypeCriterion sequences containing this parameter with any
--  other value than the ones listed above the receiver shall ignore 
--  the whole TPDU-TypeCriterion sequence.
--  In CAMEL phase 4, sms-SUBMIT-REPORT shall not be used and a received TPDU-TypeCriterion
--  sequence containing sms-SUBMIT-REPORT shall be wholly ignored.


D-CSI ::= SEQUENCE {
    dp-AnalysedInfoCriteriaList [0] DP-AnalysedInfoCriteriaList OPTIONAL,
    camelCapabilityHandling [1] CamelCapabilityHandling OPTIONAL,
    extensionContainer  [2] ExtensionContainer  OPTIONAL,
    notificationToCSE   [3] NULL        OPTIONAL,
    csi-Active  [4] NULL        OPTIONAL,
    ...} 
--  notificationToCSE and Csi-active shall not be present when D-CSI is sent to VLR/GMSC.
--  They may only be included in ATSI/ATM ack/NSDC message.
--  DP-AnalysedInfoCriteria and  camelCapabilityHandling shall be present in 
--  the D-CSI sequence.
--  If D-CSI is segmented, dp-AnalysedInfoCriteriaList and camelCapabilityHandling shall be 
--  present in the first segment


DP-AnalysedInfoCriteriaList  ::= SEQUENCE SIZE (1..maxNumOfDP-AnalysedInfoCriteria) OF
                DP-AnalysedInfoCriterium

maxNumOfDP-AnalysedInfoCriteria INTEGER ::= 10

DP-AnalysedInfoCriterium ::= SEQUENCE {
    dialledNumber   ISDN-AddressString,
    serviceKey  ServiceKey,
    gsmSCF-Address  ISDN-AddressString,
    defaultCallHandling DefaultCallHandling,
    extensionContainer  ExtensionContainer  OPTIONAL,
    ...}

SS-CSI ::= SEQUENCE {
    ss-CamelData    SS-CamelData,
    extensionContainer  ExtensionContainer  OPTIONAL,
    ...,
    notificationToCSE   [0] NULL        OPTIONAL,
    csi-Active  [1] NULL        OPTIONAL
--  notificationToCSE and csi-Active shall not be present when SS-CSI is sent to VLR.
--  They may only be included in ATSI/ATM ack/NSDC message.
}

SS-CamelData  ::= SEQUENCE {
    ss-EventList    SS-EventList,
    gsmSCF-Address  ISDN-AddressString,
    extensionContainer  [0] ExtensionContainer  OPTIONAL, 
    ... }


SS-EventList  ::= SEQUENCE SIZE (1..maxNumOfCamelSSEvents) OF SS-Code
    -- Actions for the following SS-Code values are defined in CAMEL Phase 3:
    -- ect      SS-Code ::= '00110001'B
    -- multiPTY SS-Code ::= '01010001'B
    -- cd       SS-Code ::= '00100100'B
    -- ccbs     SS-Code ::= '01000100'B
    -- all other SS codes shall be ignored
    -- When SS-CSI is sent to the VLR, it shall not contain a marking for ccbs.
    -- If the VLR receives SS-CSI containing a marking for ccbs, the VLR shall 
    -- discard the ccbs marking in SS-CSI.


maxNumOfCamelSSEvents INTEGER ::= 10

O-CSI ::= SEQUENCE {
    o-BcsmCamelTDPDataList  O-BcsmCamelTDPDataList,
    extensionContainer  ExtensionContainer  OPTIONAL,
    ...,
    camelCapabilityHandling [0] CamelCapabilityHandling OPTIONAL,
    notificationToCSE   [1] NULL        OPTIONAL,
    csiActive       [2] NULL        OPTIONAL}
--  notificationtoCSE and csiActive shall not be present when O-CSI is sent to VLR/GMSC.
--  They may only be included in ATSI/ATM ack/NSDC message.
--  O-CSI shall not be segmented.

O-BcsmCamelTDPDataList ::= SEQUENCE SIZE (1..maxNumOfCamelTDPData) OF
    O-BcsmCamelTDPData
    -- O-BcsmCamelTDPDataList shall not contain more than one instance of
    -- O-BcsmCamelTDPData containing the same value for o-BcsmTriggerDetectionPoint.
    -- For CAMEL Phase 2, this means that only one instance of O-BcsmCamelTDPData is allowed
    -- with o-BcsmTriggerDetectionPoint being equal to DP2.

maxNumOfCamelTDPData  INTEGER ::= 10

O-BcsmCamelTDPData ::= SEQUENCE {
    o-BcsmTriggerDetectionPoint O-BcsmTriggerDetectionPoint,
    serviceKey  ServiceKey,
    gsmSCF-Address  [0] ISDN-AddressString,
    defaultCallHandling [1] DefaultCallHandling,
    extensionContainer  [2] ExtensionContainer  OPTIONAL,
    ...
    }

ServiceKey ::= INTEGER (0..2147483647)

O-BcsmTriggerDetectionPoint ::= ENUMERATED {
    collectedInfo (2),
    ...,
    routeSelectFailure (4) }
    -- exception handling:
    -- For O-BcsmCamelTDPData sequences containing this parameter with any
    -- other value than the ones listed the receiver shall ignore the whole 
    -- O-BcsmCamelTDPDatasequence. 
    -- For O-BcsmCamelTDP-Criteria sequences containing this parameter with any
    -- other value than the ones listed the receiver shall ignore the whole
    -- O-BcsmCamelTDP-Criteria sequence.

O-BcsmCamelTDPCriteriaList ::= SEQUENCE SIZE (1..maxNumOfCamelTDPData) OF
    O-BcsmCamelTDP-Criteria 

T-BCSM-CAMEL-TDP-CriteriaList ::= SEQUENCE SIZE (1..maxNumOfCamelTDPData) OF
    T-BCSM-CAMEL-TDP-Criteria 

O-BcsmCamelTDP-Criteria ::= SEQUENCE {
    o-BcsmTriggerDetectionPoint O-BcsmTriggerDetectionPoint,    
    destinationNumberCriteria   [0] DestinationNumberCriteria   OPTIONAL,
    basicServiceCriteria    [1] BasicServiceCriteria    OPTIONAL,
    callTypeCriteria    [2] CallTypeCriteria    OPTIONAL,
    ...,
    o-CauseValueCriteria    [3] O-CauseValueCriteria    OPTIONAL,
    extensionContainer  [4] ExtensionContainer  OPTIONAL }

T-BCSM-CAMEL-TDP-Criteria ::= SEQUENCE {
    t-BCSM-TriggerDetectionPoint    T-BcsmTriggerDetectionPoint,    
    basicServiceCriteria    [0] BasicServiceCriteria    OPTIONAL,
    t-CauseValueCriteria    [1] T-CauseValueCriteria    OPTIONAL,
    ... }

DestinationNumberCriteria  ::= SEQUENCE {
    matchType       [0] MatchType,
    destinationNumberList   [1] DestinationNumberList   OPTIONAL,
    destinationNumberLengthList [2] DestinationNumberLengthList OPTIONAL,
    -- one or both of destinationNumberList and destinationNumberLengthList 
    -- shall be present
    ...}

DestinationNumberList  ::= SEQUENCE SIZE    (1..maxNumOfCamelDestinationNumbers) OF
                ISDN-AddressString
    -- The receiving entity shall not check the format of a number in
    -- the dialled number list

DestinationNumberLengthList  ::= SEQUENCE SIZE (1..maxNumOfCamelDestinationNumberLengths) OF 
                    INTEGER(1..maxNumOfISDN-AddressDigits)

BasicServiceCriteria   ::= SEQUENCE SIZE(1..maxNumOfCamelBasicServiceCriteria) OF
    Ext-BasicServiceCode

maxNumOfISDN-AddressDigits  INTEGER ::= 15

maxNumOfCamelDestinationNumbers  INTEGER ::= 10

maxNumOfCamelDestinationNumberLengths  INTEGER ::= 3

maxNumOfCamelBasicServiceCriteria  INTEGER ::= 5

CallTypeCriteria       ::= ENUMERATED {
    forwarded   (0),
    notForwarded    (1)}

MatchType       ::= ENUMERATED {
    inhibiting  (0),
    enabling        (1)}

O-CauseValueCriteria   ::= SEQUENCE SIZE(1..maxNumOfCAMEL-O-CauseValueCriteria) OF
    CauseValue

T-CauseValueCriteria   ::= SEQUENCE SIZE(1..maxNumOfCAMEL-T-CauseValueCriteria) OF
    CauseValue

maxNumOfCAMEL-O-CauseValueCriteria  INTEGER ::= 5

maxNumOfCAMEL-T-CauseValueCriteria  INTEGER ::= 5

CauseValue ::= OCTET STRING (SIZE(1))
-- Type extracted from Cause parameter in ITU-T Recommendation Q.763.
-- For the use of cause value refer to ITU-T Recommendation Q.850.


DefaultCallHandling ::= ENUMERATED {
    continueCall (0) ,
    releaseCall (1) ,
    ...}
    -- exception handling:
    -- reception of values in range 2-31 shall be treated as "continueCall"
    -- reception of values greater than 31 shall be treated as "releaseCall"

CamelCapabilityHandling ::= INTEGER(1..16) 
    -- value 1 = CAMEL phase 1,
    -- value 2 = CAMEL phase 2,
    -- value 3 = CAMEL Phase 3:
    -- reception of values greater than 4 shall be treated as CAMEL phase 4.

SupportedCamelPhases ::= BIT STRING {
    phase1 (0),
    phase2 (1) ,
    phase3 (2),
    phase4 (3) } (SIZE (1..16)) 
-- A node shall mark in the BIT STRING all CAMEL Phases it supports.
-- Other values than listed above shall be discarded.

OfferedCamel4CSIs ::= BIT STRING { 	
    o-csi		(0),
    d-csi		(1),
    vt-csi		(2),
    t-csi		(3),
    mt-sms-csi	(4),
    mg-csi		(5),
    psi-enhancements	(6) 
} (SIZE (7..16))
-- A node supporting Camel phase 4 shall mark in the BIT STRING all Camel4 CSIs 
-- it offers.
-- Other values than listed above shall be discarded.

OfferedCamel4Functionalities ::= BIT STRING { 	
    initiateCallAttempt	(0),
    splitLeg		(1),
    moveLeg		(2),
    disconnectLeg	(3),
    entityReleased	(4),
    dfc-WithArgument	(5),
    playTone		(6),
    dtmf-MidCall	(7),
    chargingIndicator	(8),
    alertingDP	(9),
    locationAtAlerting	(10),
    changeOfPositionDP	(11),
    or-Interactions	(12),
    warningToneEnhancements	(13),
    cf-Enhancements	(14),
    subscribedEnhancedDialledServices 	(15),
    servingNetworkEnhancedDialledServices (16),
    criteriaForChangeOfPositionDP	(17),
    serviceChangeDP	(18)

} (SIZE (15..32))
-- A node supporting Camel phase 4 shall mark in the BIT STRING all Camel4 
-- functionalities it offers.
-- Other values than listed above shall be discarded.


SMS-CSI ::= SEQUENCE {
    sms-CAMEL-TDP-DataList  [0] SMS-CAMEL-TDP-DataList  OPTIONAL,
    camelCapabilityHandling [1] CamelCapabilityHandling OPTIONAL,
    extensionContainer  [2] ExtensionContainer  OPTIONAL,
    notificationToCSE   [3] NULL        OPTIONAL,
    csi-Active  [4] NULL        OPTIONAL,
    ...}
--  notificationToCSE and csi-Active shall not be present when MO-SMS-CSI or MT-SMS-CSI is sent to VLR/SGSN.
--  They may only be included in ATSI/ATM ack/NSDC message.
--  SMS-CAMEL-TDP-Data and  camelCapabilityHandling shall be present in 
--  the SMS-CSI sequence.
--  If SMS-CSI is segmented, sms-CAMEL-TDP-DataList and camelCapabilityHandling shall be 
--  present in the first segment

SMS-CAMEL-TDP-DataList ::= SEQUENCE SIZE (1..maxNumOfCamelTDPData) OF
    SMS-CAMEL-TDP-Data
--  SMS-CAMEL-TDP-DataList shall not contain more than one instance of
--  SMS-CAMEL-TDP-Data containing the same value for sms-TriggerDetectionPoint.

SMS-CAMEL-TDP-Data ::= SEQUENCE {
    sms-TriggerDetectionPoint   [0] SMS-TriggerDetectionPoint,
    serviceKey  [1] ServiceKey,
    gsmSCF-Address  [2] ISDN-AddressString,
    defaultSMS-Handling [3] DefaultSMS-Handling,
    extensionContainer  [4] ExtensionContainer  OPTIONAL,
    ...
    }

SMS-TriggerDetectionPoint ::= ENUMERATED {
    sms-CollectedInfo (1),
    ...,
    sms-DeliveryRequest (2) }
--  exception handling:
--  For SMS-CAMEL-TDP-Data and MT-smsCAMELTDP-Criteria sequences containing this parameter with any
--  other value than the ones listed the receiver shall ignore the whole 
--  SMS-CAMEL-TDP-Data sequence.
--
--  If this parameter is received with any other value than sms-CollectedInfo
--  in an SMS-CAMEL-TDP-Data sequence contained in mo-sms-CSI, then the receiver 
--  shall ignore the whole SMS-CAMEL-TDP-Data sequence.
--
--  If this parameter is received with any other value than sms-DeliveryRequest
--  in an SMS-CAMEL-TDP-Data sequence contained in mt-sms-CSI then the receiver 
--  shall ignore the whole SMS-CAMEL-TDP-Data sequence.
--
--  If this parameter is received with any other value than sms-DeliveryRequest
--  in an MT-smsCAMELTDP-Criteria sequence then the receiver shall
--  ignore the whole MT-smsCAMELTDP-Criteria sequence.


DefaultSMS-Handling ::= ENUMERATED {
    continueTransaction (0) ,
    releaseTransaction (1) ,
    ...}
--  exception handling:
--  reception of values in range 2-31 shall be treated as "continueTransaction"
--  reception of values greater than 31 shall be treated as "releaseTransaction"

M-CSI ::= SEQUENCE {
    mobilityTriggers    MobilityTriggers,
    serviceKey  ServiceKey,
    gsmSCF-Address  [0] ISDN-AddressString,
    extensionContainer  [1] ExtensionContainer  OPTIONAL,
    notificationToCSE   [2] NULL        OPTIONAL,
    csi-Active  [3] NULL        OPTIONAL,
    ...}
--  notificationToCSE and csi-Active shall not be present when M-CSI is sent to VLR.
--  They may only be included in ATSI/ATM ack/NSDC message.

MG-CSI ::= SEQUENCE {
    mobilityTriggers	MobilityTriggers,
    serviceKey	ServiceKey,
    gsmSCF-Address	[0]	ISDN-AddressString,
    extensionContainer	[1]	ExtensionContainer	OPTIONAL,
    notificationToCSE	[2] NULL		OPTIONAL,
    csi-Active	[3] NULL		OPTIONAL,
    ...}
--  notificationToCSE and csi-Active shall not be present when MG-CSI is sent to 
--  SGSN.
--  They may only be included in ATSI/ATM ack/NSDC message.

MobilityTriggers  ::= SEQUENCE SIZE (1..maxNumOfMobilityTriggers) OF
    MM-Code

maxNumOfMobilityTriggers INTEGER ::= 10

MM-Code ::= OCTET STRING (SIZE (1))
--  This type is used to indicate a Mobility Management event.
--  Actions for the following MM-Code values are defined in CAMEL Phase 4:
--
--  Location-update-in-same-VLR MM-Code ::= '00000000'B
--  Location-update-to-other-VLR    MM-Code ::= '00000001'B
--  IMSI-Attach MM-Code ::= '00000010'B
--  MS-initiated-IMSI-Detach    MM-Code ::= '00000011'B
--  Network-initiated-IMSI-Detach   MM-Code ::= '00000100'B
--
--  PS domain MM events:
--  Routeing-Area-update-in-same-SGSN	MM-Code ::= '10000000'B
--  Routeing-Area-update-to-other-SGSN-update-from-new-SGSN
--  			MM-Code ::= '10000001'B
--  Routeing-Area-update-to-other-SGSN-disconnect-by-detach
--  			MM-Code ::= '10000010'B
--  GPRS-Attach	MM-Code ::= '10000011'B
--  MS-initiated-GPRS-Detach	MM-Code ::= '10000100'B
--  Network-initiated-GPRS-Detach	MM-Code ::= '10000101'B 
--  Network-initiated-transfer-to-MS-not-reachable-for-paging
--  			MM-Code ::= '10000110'B
--
--  If the MSC receives any other MM-code than the ones listed above for the
--  CS domain, then the MSC shall ignore that MM-code.
--  If the SGSN receives any other MM-code than the ones listed above for the
--  PS domain, then the SGSN shall ignore that MM-code.


T-CSI ::= SEQUENCE {
    t-BcsmCamelTDPDataList  T-BcsmCamelTDPDataList,
    extensionContainer  ExtensionContainer  OPTIONAL,
    ...,
    camelCapabilityHandling [0] CamelCapabilityHandling OPTIONAL,
    notificationToCSE   [1] NULL        OPTIONAL,
    csi-Active  [2] NULL        OPTIONAL}
--  notificationToCSE and csi-Active shall not be present when VT-CSI/T-CSI is sent
--  to VLR/GMSC.
--  They may only be included in ATSI/ATM ack/NSDC message.
--	T-CSI shall not be segmented.

T-BcsmCamelTDPDataList ::= SEQUENCE SIZE (1..maxNumOfCamelTDPData) OF
    T-BcsmCamelTDPData
    --- T-BcsmCamelTDPDataList shall not contain more than one instance of
    --- T-BcsmCamelTDPData containing the same value for t-BcsmTriggerDetectionPoint.
    --- For CAMEL Phase 2, this means that only one instance of T-BcsmCamelTDPData is allowed
    --- with t-BcsmTriggerDetectionPoint being equal to DP12. 
    --- For CAMEL Phase 3, more TDP's are allowed.

T-BcsmCamelTDPData ::= SEQUENCE {
    t-BcsmTriggerDetectionPoint T-BcsmTriggerDetectionPoint,
    serviceKey  ServiceKey,
    gsmSCF-Address  [0] ISDN-AddressString,
    defaultCallHandling [1] DefaultCallHandling,
    extensionContainer  [2] ExtensionContainer  OPTIONAL,
    ...}

T-BcsmTriggerDetectionPoint ::= ENUMERATED {
    termAttemptAuthorized (12),
    ... ,
    tBusy (13),
    tNoAnswer (14)}
    -- exception handling:
    -- For T-BcsmCamelTDPData sequences containing this parameter with any other
    -- value than the ones listed above, the receiver shall ignore the whole
    -- T-BcsmCamelTDPData sequence.


-- gprs location information retrieval types

SendRoutingInfoForGprsArg ::= SEQUENCE {
    imsi                [0] IMSI,
    ggsn-Address        [1] GSN-Address OPTIONAL, 
    ggsn-Number     [2] ISDN-AddressString,
    extensionContainer      [3] ExtensionContainer  OPTIONAL,
    ...}

SendRoutingInfoForGprsRes ::= SEQUENCE {
    sgsn-Address        [0] GSN-Address,
    ggsn-Address        [1] GSN-Address OPTIONAL,
    mobileNotReachableReason        [2] AbsentSubscriberDiagnosticSM        OPTIONAL,
    extensionContainer      [3] ExtensionContainer  OPTIONAL,
    ...}

-- failure report types

FailureReportArg ::= SEQUENCE {
    imsi                [0] IMSI,
    ggsn-Number     [1] ISDN-AddressString  ,
    ggsn-Address        [2] GSN-Address OPTIONAL,
    extensionContainer      [3] ExtensionContainer  OPTIONAL,
    ...}

FailureReportRes ::= SEQUENCE {
    ggsn-Address        [0] GSN-Address OPTIONAL,
    extensionContainer      [1] ExtensionContainer  OPTIONAL,
    ...}

-- gprs notification types

NoteMsPresentForGprsArg ::= SEQUENCE {
    imsi                [0] IMSI,
    sgsn-Address        [1] GSN-Address,
    ggsn-Address        [2] GSN-Address OPTIONAL,
    extensionContainer      [3] ExtensionContainer  OPTIONAL,
    ...}

NoteMsPresentForGprsRes ::= SEQUENCE {
    extensionContainer      [0] ExtensionContainer  OPTIONAL,
    ...}


-- fault recovery types

ResetArg ::= SEQUENCE {
    hlr-Number  ISDN-AddressString,
    hlr-List        HLR-List        OPTIONAL,
    ...}

RestoreDataArg ::= SEQUENCE {
    imsi            IMSI,
    lmsi            LMSI            OPTIONAL,
    extensionContainer  ExtensionContainer  OPTIONAL,
    ... ,
    vlr-Capability  [6] VLR-Capability  OPTIONAL }

RestoreDataRes ::= SEQUENCE {
    hlr-Number  ISDN-AddressString,
    msNotReachable  NULL            OPTIONAL,
    extensionContainer  ExtensionContainer  OPTIONAL,
    ...}

-- VBS/VGCS types
VBSDataList ::= SEQUENCE SIZE (1..maxNumOfVBSGroupIds) OF
                VoiceBroadcastData

VGCSDataList ::= SEQUENCE SIZE (1..maxNumOfVGCSGroupIds) OF
                VoiceGroupCallData

maxNumOfVBSGroupIds  INTEGER ::= 50

maxNumOfVGCSGroupIds  INTEGER ::= 50

VoiceGroupCallData  ::= SEQUENCE {
    groupId     GroupId,
    extensionContainer  ExtensionContainer  OPTIONAL,
    ...}

VoiceBroadcastData ::= SEQUENCE {
    groupid     GroupId,
    broadcastInitEntitlement    NULL            OPTIONAL,
    extensionContainer  ExtensionContainer  OPTIONAL,
    ...}

GroupId  ::= OCTET STRING (SIZE (3))
    -- Refers to the Group Identification as specified in GSM TS 03.03 
    -- and 03.68/ 03.69

-- provide subscriber info types

ProvideSubscriberInfoArg ::= SEQUENCE {
    imsi        [0] IMSI,
    lmsi        [1] LMSI    OPTIONAL,
    requestedInfo   [2] RequestedInfo,
    extensionContainer  [3] ExtensionContainer  OPTIONAL,
    ...}

ProvideSubscriberInfoRes ::= SEQUENCE {
    subscriberInfo  SubscriberInfo,
    extensionContainer  ExtensionContainer  OPTIONAL,
    ...}

SubscriberInfo ::= SEQUENCE {
    locationInformation [0] LocationInformation OPTIONAL,
    subscriberState [1] SubscriberState OPTIONAL,
    extensionContainer  [2] ExtensionContainer  OPTIONAL,
    ...,
    locationInformationGPRS	[3] LocationInformationGPRS	OPTIONAL,
    ps-SubscriberState	[4] PS-SubscriberState	OPTIONAL,
    imei			[5] IMEI		OPTIONAL,
    ms-Classmark2	[6] MS-Classmark2	OPTIONAL,
    gprs-MS-Class	[7] GPRSMSClass	OPTIONAL,
    mnpInfoRes	[8] MNPInfoRes	OPTIONAL}
--  If the HLR receives locationInformation, subscriberState or ms-Classmark2 
--  from an SGSN it shall discard them.
--  If the HLR receives locationInformationGPRS, ps-SubscriberState or gprs-MS-
--  Class from a VLR it shall discard them.
--  If the HLR receives parameters which it has not requested, it shall discard 
--  them.
MNPInfoRes ::= SEQUENCE {
	routeingNumber	[0] RouteingNumber 	OPTIONAL,
	imsi			[1] IMSI		OPTIONAL,
	msisdn		[2] ISDN-AddressString 	OPTIONAL,
	numberPortabilityStatus	[3] NumberPortabilityStatus	OPTIONAL,
	extensionContainer	[4] ExtensionContainer	OPTIONAL,
	... }
--The IMSI parameter contains a generic IMSI, i.e. it is not tied necessarily to the 
--Subscriber. MCC and MNC values in this IMSI shall point to the Subscription Network of 
--the Subscriber. See 3GPP TS 23.066 [108].

RouteingNumber ::= TBCD-STRING (SIZE (1..5))

NumberPortabilityStatus ::= ENUMERATED {
	notKnownToBePorted	(0),
	ownNumberPortedOut	(1),
	foreignNumberPortedToForeignNetwork	(2),
	...,
	ownNumberNotPortedOut	(4),
	foreignNumberPortedIn	(5)
	}
	--	exception handling: 
	--  reception of other values than the ones listed the receiver shall ignore the 
	--  whole NumberPortabilityStatus;
	--  ownNumberNotPortedOut or foreignNumberPortedIn may only be included in Any Time 
	--  Interrogation message.

MS-Classmark2 ::= OCTET STRING (SIZE (3))
    -- This parameter carries the value part of the MS Classmark 2 IE defined in 
    -- 3GPP TS 24.008 [35].

GPRSMSClass ::= SEQUENCE {
    mSNetworkCapability	[0] MSNetworkCapability,
    mSRadioAccessCapability	[1] MSRadioAccessCapability	OPTIONAL
    }

MSNetworkCapability ::= OCTET STRING (SIZE (1..8))
    -- This parameter carries the value part of the MS Network Capability IE 
    -- defined in 3GPP TS 24.008 [35].
	
MSRadioAccessCapability ::= OCTET STRING (SIZE (1..50))
    -- This parameter carries the value part of the MS Radio Access Capability 
    -- IE defined in 3GPP TS 24.008 [35].


RequestedInfo ::= SEQUENCE {
    locationInformation [0] NULL        OPTIONAL,
    subscriberState [1] NULL        OPTIONAL,
    extensionContainer  [2] ExtensionContainer  OPTIONAL,
    ..., 
    currentLocation [3] NULL        OPTIONAL,
    requestedDomain	[4] DomainType	OPTIONAL,
    imei			[6] NULL		OPTIONAL,
    ms-classmark	[5] NULL		OPTIONAL,
    mnpRequestedInfo	[7] NULL 		OPTIONAL  }
-- currentLocation shall not be present if locationInformation 
-- is absent

DomainType ::=  ENUMERATED {
    cs-Domain		(0),
    ps-Domain		(1),
    ...}
-- exception handling:
-- reception of values > 1 shall be mapped to 'cs-Domain'


LocationInformation ::= SEQUENCE {
    ageOfLocationInformation    AgeOfLocationInformation    OPTIONAL,
    geographicalInformation [0] GeographicalInformation OPTIONAL,
    vlr-number  [1] ISDN-AddressString  OPTIONAL,
    locationNumber  [2] LocationNumber  OPTIONAL,
    cellGlobalIdOrServiceAreaIdOrLAI    [3] CellGlobalIdOrServiceAreaIdOrLAI    OPTIONAL,
    extensionContainer  [4] ExtensionContainer  OPTIONAL,
    ... ,
    selectedLSA-Id  [5] LSAIdentity OPTIONAL,
    msc-Number  [6] ISDN-AddressString  OPTIONAL,
    geodeticInformation [7] GeodeticInformation OPTIONAL, 
    currentLocationRetrieved    [8] NULL        OPTIONAL,
    sai-Present [9] NULL        OPTIONAL }
-- sai-Present indicates that the cellGlobalIdOrServiceAreaIdOrLAI parameter contains
-- a Service Area Identity.
-- currentLocationRetrieved shall be present 
-- if the location information were retrieved after a successfull paging.

LocationInformationGPRS ::= SEQUENCE {
    cellGlobalIdOrServiceAreaIdOrLAI	[0] CellGlobalIdOrServiceAreaIdOrLAI OPTIONAL,
    routeingAreaIdentity	[1] RAIdentity	OPTIONAL,
    geographicalInformation	[2] GeographicalInformation	OPTIONAL,
    sgsn-Number	[3] ISDN-AddressString	OPTIONAL,
    selectedLSAIdentity	[4] LSAIdentity	OPTIONAL,
    extensionContainer	[5] ExtensionContainer	OPTIONAL,
    ...,
    sai-Present	[6] NULL		OPTIONAL,
    geodeticInformation	[7] GeodeticInformation	OPTIONAL,
    currentLocationRetrieved	[8] NULL		OPTIONAL,
    ageOfLocationInformation	[9] AgeOfLocationInformation	OPTIONAL }
    -- sai-Present indicates that the cellGlobalIdOrServiceAreaIdOrLAI parameter 
    -- contains a Service Area Identity.
    -- currentLocationRetrieved shall be present if the location information
    -- was retrieved after successful paging.

RAIdentity ::= OCTET STRING (SIZE (6))
    -- Routing Area Identity is coded in accordance with 3GPP TS 29.060 [105].
    -- It shall contain the value part defined in 3GPP TS 29.060 only. I.e. the 
    -- 3GPP TS 29.060 type identifier octet shall not be included.

GeographicalInformation ::= OCTET STRING (SIZE (8))
--  Refers to geographical Information defined in 3GPP TS 23.032.
--  Only the description of an ellipsoid point with uncertainty circle
--  as specified in 3GPP TS 23.032 is allowed to be used
--  The internal structure according to 3GPP TS 23.032 is as follows:
--      Type of shape (ellipsoid point with uncertainty circle) 1 octet
--      Degrees of Latitude             3 octets
--      Degrees of Longitude                3 octets
--      Uncertainty code                1 octet

GeodeticInformation ::= OCTET STRING (SIZE (10))
--  Refers to Calling Geodetic Location defined in Q.763 (1999).
--  Only the description of an ellipsoid point with uncertainty circle
--  as specified in Q.763 (1999) is allowed to be used
--  The internal structure according to Q.763 (1999) is as follows:
--      Screening and presentation indicators       1 octet
--      Type of shape (ellipsoid point with uncertainty circle) 1 octet
--      Degrees of Latitude             3 octets
--      Degrees of Longitude                3 octets
--      Uncertainty code                1 octet
--      Confidence              1 octet

LocationNumber ::= OCTET STRING (SIZE (2..10))
    -- the internal structure is defined in CCITT Rec Q.763

SubscriberState ::= CHOICE {
    assumedIdle [0] NULL,
    camelBusy   [1] NULL,
    netDetNotReachable  NotReachableReason,
    notProvidedFromVLR  [2] NULL}

PS-SubscriberState ::= CHOICE {
    notProvidedFromSGSN	[0] NULL,
    ps-Detached	[1] NULL,
    ps-AttachedNotReachableForPaging	[2] NULL,
    ps-AttachedReachableForPaging	[3] NULL,
    ps-PDP-ActiveNotReachableForPaging	[4] PDP-ContextInfoList,
    ps-PDP-ActiveReachableForPaging	[5] PDP-ContextInfoList,
    netDetNotReachable	NotReachableReason }

PDP-ContextInfoList ::= SEQUENCE SIZE (1..maxNumOfPDP-Contexts) OF
				PDP-ContextInfo

PDP-ContextInfo ::= SEQUENCE {
    pdp-ContextIdentifier	[0] ContextId,
    pdp-ContextActive	[1] NULL		OPTIONAL,
    pdp-Type		[2] PDP-Type,
    pdp-Address	[3] PDP-Address	OPTIONAL,
    apn-Subscribed	[4] APN		OPTIONAL,
    apn-InUse		[5] APN		OPTIONAL,
    nsapi		[6] NSAPI		OPTIONAL,
    transactionId	[7] TransactionId	OPTIONAL,
    teid-ForGnAndGp	[8] TEID		OPTIONAL,
    teid-ForIu	[9] TEID		OPTIONAL,
    ggsn-Address	[10] GSN-Address 	OPTIONAL,
    qos-Subscribed	[11] Ext-QoS-Subscribed	OPTIONAL,
    qos-Requested	[12] Ext-QoS-Subscribed	OPTIONAL,
    qos-Negotiated	[13] Ext-QoS-Subscribed	OPTIONAL,
    chargingId	[14] GPRSChargingID	OPTIONAL,
    chargingCharacteristics	[15] ChargingCharacteristics	OPTIONAL,
    rnc-Address	[16] GSN-Address	OPTIONAL,
    extensionContainer	[17] ExtensionContainer	OPTIONAL,
    ...,
    qos2-Subscribed	[18] Ext2-QoS-Subscribed	OPTIONAL,
    -- qos2-Subscribed may be present only if qos-Subscribed is present.
    qos2-Requested	[19] Ext2-QoS-Subscribed	OPTIONAL,
    -- qos2-Requested may be present only if qos-Requested is present.
    qos2-Negotiated	[20] Ext2-QoS-Subscribed	OPTIONAL
    -- qos2-Negotiated may be present only if qos-Negotiated is present.
}

NSAPI ::= INTEGER (0..15)
--  This type is used to indicate the Network layer Service Access Point

TransactionId ::= OCTET STRING (SIZE (1..2))
--  This type carries the value part of the transaction identifier which is used 
--  in the session management messages on the access interface. The encoding is 
--  defined in 3GPP TS 24.008

TEID ::= OCTET STRING (SIZE (4))
--  This type carries the value part of the Tunnel Endpoint Identifier which is 
--  used to distinguish between different tunnels between the same pair of 
--  entities which communicate using the GPRS Tunnelling Protocol The encoding 
--  is defined in 3GPP TS 29.060.

GPRSChargingID ::= OCTET STRING (SIZE (4))
--  The Charging ID is a unique four octet value generated by the GGSN when 
--  a PDP Context is activated. A Charging ID is generated for each activated 
--  context.
--  The encoding is defined in 3GPP TS 29.060.

NotReachableReason ::= ENUMERATED {
    msPurged (0),
    imsiDetached (1),
    restrictedArea (2),
    notRegistered (3)}

-- any time interrogation info types

AnyTimeInterrogationArg ::= SEQUENCE {
    subscriberIdentity  [0] SubscriberIdentity,
    requestedInfo   [1] RequestedInfo,
    gsmSCF-Address  [3] ISDN-AddressString,
    extensionContainer  [2] ExtensionContainer  OPTIONAL,
    ...}

AnyTimeInterrogationRes ::= SEQUENCE {
    subscriberInfo  SubscriberInfo,
    extensionContainer  ExtensionContainer  OPTIONAL,
    ...}


-- any time information handling types

AnyTimeSubscriptionInterrogationArg ::= SEQUENCE {
    subscriberIdentity  [0] SubscriberIdentity,
    requestedSubscriptionInfo   [1] RequestedSubscriptionInfo,
    gsmSCF-Address  [2] ISDN-AddressString,
    extensionContainer  [3] ExtensionContainer  OPTIONAL,
    longFTN-Supported   [4] NULL        OPTIONAL,
    ...}

AnyTimeSubscriptionInterrogationRes ::= SEQUENCE {
    callForwardingData  [1] CallForwardingData  OPTIONAL,
    callBarringData [2] CallBarringData OPTIONAL,
    odb-Info        [3] ODB-Info    OPTIONAL,
    camel-SubscriptionInfo  [4] CAMEL-SubscriptionInfo  OPTIONAL,
    supportedVLR-CAMEL-Phases   [5] SupportedCamelPhases    OPTIONAL,
    supportedSGSN-CAMEL-Phases  [6] SupportedCamelPhases    OPTIONAL,
    extensionContainer  [7] ExtensionContainer  OPTIONAL,
    ...,
    offeredCamel4CSIsInVLR	[8] OfferedCamel4CSIs	OPTIONAL,
    offeredCamel4CSIsInSGSN	[9] OfferedCamel4CSIs	OPTIONAL }

RequestedSubscriptionInfo ::= SEQUENCE {
    requestedSS-Info    [1] SS-ForBS-Code   OPTIONAL,
    odb         [2] NULL        OPTIONAL,
    requestedCAMEL-SubscriptionInfo [3] RequestedCAMEL-SubscriptionInfo     OPTIONAL,
    supportedVLR-CAMEL-Phases   [4] NULL        OPTIONAL,
    supportedSGSN-CAMEL-Phases  [5] NULL        OPTIONAL,
    extensionContainer  [6] ExtensionContainer  OPTIONAL,
    ...,
    additionalRequestedCAMEL-SubscriptionInfo
				[7] AdditionalRequestedCAMEL-SubscriptionInfo
							OPTIONAL }

RequestedCAMEL-SubscriptionInfo ::= ENUMERATED {
    o-CSI       (0),
    t-CSI       (1),
    vt-CSI      (2),
    tif-CSI     (3),
    gprs-CSI        (4),
    mo-sms-CSI     (5),
    ss-CSI      (6),
    m-CSI       (7),
    d-csi       (8)}

AdditionalRequestedCAMEL-SubscriptionInfo ::= ENUMERATED {
    mt-sms-CSI	(0),
    mg-csi		(1),
    o-IM-CSI 		(2),
    d-IM-CSI		(3),
    vt-IM-CSI	 	(4),
    ...}
--  exception handling: unknown values shall be discarded by the receiver.


CallForwardingData ::= SEQUENCE {
    forwardingFeatureList   Ext-ForwFeatureList,
    notificationToCSE   NULL            OPTIONAL,
    extensionContainer  [0] ExtensionContainer  OPTIONAL,
    ...}

CallBarringData ::= SEQUENCE {
    callBarringFeatureList  Ext-CallBarFeatureList,
    password        Password,
    wrongPasswordAttemptsCounter    WrongPasswordAttemptsCounter,
    notificationToCSE   NULL            OPTIONAL,
    extensionContainer  ExtensionContainer  OPTIONAL,
    ...}

WrongPasswordAttemptsCounter ::= INTEGER (0..4)

ODB-Info ::= SEQUENCE {
    odb-Data        ODB-Data,
    notificationToCSE   NULL            OPTIONAL,
    extensionContainer  ExtensionContainer  OPTIONAL,
    ...}

CAMEL-SubscriptionInfo ::= SEQUENCE {
    o-CSI       [0] O-CSI   OPTIONAL,
    o-BcsmCamelTDP-CriteriaList [1] O-BcsmCamelTDPCriteriaList  OPTIONAL, 
    d-CSI       [2] D-CSI   OPTIONAL,
    t-CSI       [3] T-CSI   OPTIONAL,
    t-BCSM-CAMEL-TDP-CriteriaList   [4] T-BCSM-CAMEL-TDP-CriteriaList   OPTIONAL,
    vt-CSI      [5] T-CSI   OPTIONAL,
    vt-BCSM-CAMEL-TDP-CriteriaList  [6] T-BCSM-CAMEL-TDP-CriteriaList   OPTIONAL,
    tif-CSI     [7] NULL        OPTIONAL,
    tif-CSI-NotificationToCSE   [8] NULL        OPTIONAL,
    gprs-CSI        [9] GPRS-CSI    OPTIONAL,
    mo-sms-CSI     [10]    SMS-CSI OPTIONAL,
    ss-CSI      [11]    SS-CSI  OPTIONAL,
    m-CSI       [12]    M-CSI   OPTIONAL,
    extensionContainer  [13]    ExtensionContainer  OPTIONAL,
    ...,
    specificCSIDeletedList	[14]	SpecificCSI-Withdraw	OPTIONAL,
    mt-sms-CSI	[15]	SMS-CSI	OPTIONAL,
    mt-smsCAMELTDP-CriteriaList	[16]	MT-smsCAMELTDP-CriteriaList	OPTIONAL,
    mg-csi		[17]	MG-CSI	OPTIONAL,
    o-IM-CSI		[18] O-CSI	OPTIONAL,
    o-IM-BcsmCamelTDP-CriteriaList	[19] O-BcsmCamelTDPCriteriaList	OPTIONAL,
    d-IM-CSI		[20] D-CSI	OPTIONAL,
    vt-IM-CSI		[21] T-CSI	OPTIONAL,
    vt-IM-BCSM-CAMEL-TDP-CriteriaList	[22]	T-BCSM-CAMEL-TDP-CriteriaList	OPTIONAL }

AnyTimeModificationArg ::= SEQUENCE {
    subscriberIdentity  [0] SubscriberIdentity,
    gsmSCF-Address  [1] ISDN-AddressString,
    modificationRequestFor-CF-Info  [2] ModificationRequestFor-CF-Info OPTIONAL,
    modificationRequestFor-CB-Info  [3] ModificationRequestFor-CB-Info OPTIONAL,
    modificationRequestFor-CSI  [4] ModificationRequestFor-CSI  OPTIONAL,
    extensionContainer  [5] ExtensionContainer  OPTIONAL,
    longFTN-Supported   [6] NULL        OPTIONAL,
    ...,
    modificationRequestFor-ODB-data	[7]	ModificationRequestFor-ODB-data OPTIONAL }

AnyTimeModificationRes ::= SEQUENCE {
    ss-InfoFor-CSE  [0] Ext-SS-InfoFor-CSE  OPTIONAL,
    camel-SubscriptionInfo  [1] CAMEL-SubscriptionInfo  OPTIONAL,
    extensionContainer  [2] ExtensionContainer  OPTIONAL,
    ...,
    odb-Info		[3]	ODB-Info	OPTIONAL}

ModificationRequestFor-CF-Info ::= SEQUENCE {
    ss-Code     [0] SS-Code,
    basicService    [1] Ext-BasicServiceCode    OPTIONAL,
    ss-Status       [2] Ext-SS-Status   OPTIONAL,
    forwardedToNumber   [3] AddressString   OPTIONAL,
    forwardedToSubaddress   [4] ISDN-SubaddressString   OPTIONAL,
    noReplyConditionTime    [5] Ext-NoRepCondTime   OPTIONAL,
    modifyNotificationToCSE [6] ModificationInstruction OPTIONAL,
    extensionContainer  [7] ExtensionContainer  OPTIONAL,
    ...}

ModificationRequestFor-CB-Info ::= SEQUENCE {
    ss-Code     [0] SS-Code,
    basicService    [1] Ext-BasicServiceCode    OPTIONAL,
    ss-Status       [2] Ext-SS-Status   OPTIONAL,
    password        [3] Password    OPTIONAL,
    wrongPasswordAttemptsCounter    [4] WrongPasswordAttemptsCounter    OPTIONAL,
    modifyNotificationToCSE [5] ModificationInstruction OPTIONAL,
    extensionContainer  [6] ExtensionContainer  OPTIONAL,
    ...}

ModificationRequestFor-ODB-data ::= SEQUENCE {
    odb-data		[0]	ODB-Data	OPTIONAL,
    modifyNotificationToCSE	[1]	ModificationInstruction	OPTIONAL,
    extensionContainer	[2]	ExtensionContainer	OPTIONAL,
    ...}


ModificationRequestFor-CSI ::= SEQUENCE {
    requestedCamel-SubscriptionInfo [0] RequestedCAMEL-SubscriptionInfo,
    modifyNotificationToCSE [1] ModificationInstruction OPTIONAL,
    modifyCSI-State [2] ModificationInstruction OPTIONAL,
    extensionContainer  [3] ExtensionContainer  OPTIONAL,
    ...,
    additionalRequestedCAMEL-SubscriptionInfo
				[4] AdditionalRequestedCAMEL-SubscriptionInfo
							OPTIONAL }
    -- requestedCamel-SubscriptionInfo shall be discarded if
    -- additionalRequestedCAMEL-SubscriptionInfo is received

ModificationInstruction ::= ENUMERATED {
    deactivate  (0),
    activate        (1)}

-- subscriber data modification notification types

NoteSubscriberDataModifiedArg ::= SEQUENCE {
    imsi            IMSI,
    msisdn      ISDN-AddressString,
    forwardingInfoFor-CSE   [0] Ext-ForwardingInfoFor-CSE   OPTIONAL,
    callBarringInfoFor-CSE  [1] Ext-CallBarringInfoFor-CSE  OPTIONAL,
    odb-Info        [2] ODB-Info    OPTIONAL,
    camel-SubscriptionInfo  [3] CAMEL-SubscriptionInfo  OPTIONAL,
    allInformationSent  [4] NULL        OPTIONAL,
    extensionContainer  ExtensionContainer  OPTIONAL,
    ...}

NoteSubscriberDataModifiedRes ::= SEQUENCE {
    extensionContainer  ExtensionContainer  OPTIONAL,
    ...}


-- mobility management event notificatioon info types

NoteMM-EventArg::= SEQUENCE {
    serviceKey  ServiceKey,
    eventMet        [0] MM-Code,
    imsi            [1] IMSI,
    msisdn      [2] ISDN-AddressString,
    locationInformation [3] LocationInformation OPTIONAL,
    supportedCAMELPhases    [5] SupportedCamelPhases    OPTIONAL,
    extensionContainer  [6] ExtensionContainer  OPTIONAL,
    ...,
    locationInformationGPRS	[7]	LocationInformationGPRS	OPTIONAL,
    offeredCamel4Functionalities	[8] OfferedCamel4Functionalities	OPTIONAL }

NoteMM-EventRes ::= SEQUENCE {
    extensionContainer  ExtensionContainer  OPTIONAL,
    ...}

Ext-SS-InfoFor-CSE ::= CHOICE {
    forwardingInfoFor-CSE   [0] Ext-ForwardingInfoFor-CSE,
    callBarringInfoFor-CSE  [1] Ext-CallBarringInfoFor-CSE
    }

Ext-ForwardingInfoFor-CSE ::= SEQUENCE {
    ss-Code     [0] SS-Code,
    forwardingFeatureList   [1] Ext-ForwFeatureList,
    notificationToCSE   [2] NULL,
    extensionContainer  [3] ExtensionContainer  OPTIONAL,
    ...}

Ext-CallBarringInfoFor-CSE ::= SEQUENCE {
    ss-Code     [0] SS-Code,
    callBarringFeatureList  [1] Ext-CallBarFeatureList,
    password        [2] Password,
    wrongPasswordAttemptsCounter    [3] WrongPasswordAttemptsCounter,
    notificationToCSE   [4] NULL,
    extensionContainer  [5] ExtensionContainer  OPTIONAL,
    ...}

--not used 
--not used END
--not used  

--------------------------------------------------------------------------------
--------------------------------------------------------------------------------
--------------------------------------------------------------------------------
--[CL] 29002-560.doc 17.7.2 Operation and maintenance data types

-- Module ----------------------------------------------------------------------
--------------------------------------------------------------------------------
-- MAP OM Data Types.
--------------------------------------------------------------------------------
--------------------------------------------------------------------------------

 
--not used MAP-OM-DataTypes {
--not used    ccitt identified-organization (4) etsi (0) mobileDomain (0)
--not used    gsm-Network (1) modules (3) map-OM-DataTypes (12) version8 (8)}
--not used 
--not used DEFINITIONS
--not used 
--not used IMPLICIT TAGS
--not used 
--not used ::=
--not used 
--not used BEGIN
--not used 
--not used EXPORTS
--not used     ActivateTraceModeArg,
--not used     ActivateTraceModeRes,
--not used     DeactivateTraceModeArg,
--not used     DeactivateTraceModeRes
--not used ;
--not used 
--not used IMPORTS
--not used     AddressString,
--not used     IMSI
--not used FROM MAP-CommonDataTypes {
--not used    ccitt identified-organization (4) etsi (0) mobileDomain (0)
--not used    gsm-Network (1) modules (3) map-CommonDataTypes (18) version8 (8)}
--not used 
--not used     ExtensionContainer
--not used FROM MAP-ExtensionDataTypes {
--not used    ccitt identified-organization (4) etsi (0) mobileDomain (0)
--not used    gsm-Network (1) modules (3) map-ExtensionDataTypes (21) version8 (8)}
--not used 
--not used 
--not used ;
--not used 

ActivateTraceModeArg ::= SEQUENCE {
    imsi            [0] IMSI        OPTIONAL,
    traceReference  [1] TraceReference,
    traceType       [2] TraceType,
    omc-Id      [3] AddressString   OPTIONAL,
    extensionContainer  [4] ExtensionContainer  OPTIONAL,
    ...,
    traceReference2	[5] TraceReference2	OPTIONAL,
	traceDepthList	[6] TraceDepthList	OPTIONAL,
	traceNE-TypeList	[7] TraceNE-TypeList	OPTIONAL,
	traceInterfaceList	[8] TraceInterfaceList	OPTIONAL,
	traceEventList	[9] TraceEventList	OPTIONAL
}

TraceReference ::= OCTET STRING (SIZE (1..2))
TraceReference2 ::= OCTET STRING (SIZE (3))
TraceType ::= INTEGER
    (0..255)
    -- Trace types are fully defined in TS GSM 12.08.
TraceDepthList ::= SEQUENCE {
	msc-s-TraceDepth	[0] TraceDepth	OPTIONAL,
	mgw-TraceDepth	[1] TraceDepth	OPTIONAL,
	sgsn-TraceDepth	[2] TraceDepth	OPTIONAL,
	ggsn-TraceDepth	[3] TraceDepth	OPTIONAL,
	rnc-TraceDepth	[4] TraceDepth	OPTIONAL,
	bmsc-TraceDepth	[5] TraceDepth	OPTIONAL,
	...}
TraceDepth ::= ENUMERATED {
	minimum (0),
	medium (1),
	maximum (2),
	...}
-- The value medium is applicable only for RNC. For other network elements, if value medium
-- is received, value minimum shall be applied.
TraceNE-TypeList ::= BIT STRING {
	msc-s (0),
	mgw (1),
	sgsn (2),
	ggsn (3),
	rnc (4),
	bm-sc (5)} (SIZE (6..16))
-- Other bits than listed above shall be discarded.
TraceInterfaceList ::= SEQUENCE {
	msc-s-List	[0] MSC-S-InterfaceList	OPTIONAL,
	mgw-List		[1] MGW-InterfaceList	OPTIONAL,
	sgsn-List		[2] SGSN-InterfaceList	OPTIONAL,
	ggsn-List		[3] GGSN-InterfaceList	OPTIONAL,
	rnc-List		[4] RNC-InterfaceList	OPTIONAL,
	bmsc-List		[5] BMSC-InterfaceList	OPTIONAL,
	...}
MSC-S-InterfaceList ::= BIT STRING {
	a (0),
	iu (1),
	mc (2),
	map-g (3),
	map-b (4),
	map-e (5),
	map-f (6),
	cap (7),
	map-d (8),
	map-c (9)} (SIZE (10..16))
-- Other bits than listed above shall be discarded.
MGW-InterfaceList ::= BIT STRING {
	mc (0),
	nb-up (1),
	iu-up (2)} (SIZE (3..8))
-- Other bits than listed above shall be discarded.
SGSN-InterfaceList ::= BIT STRING {
	gb (0),
	iu (1),
	gn (2),
	map-gr (3),
	map-gd (4),
	map-gf (5),
	gs (6),
	ge (7)} (SIZE (8..16))
-- Other bits than listed above shall be discarded.
GGSN-InterfaceList ::= BIT STRING {
	gn (0),
	gi (1),
	gmb (2)} (SIZE (3..8))
-- Other bits than listed above shall be discarded
RNC-InterfaceList ::= BIT STRING {
	iu (0),
	iur (1),
	iub (2),
	uu (3)} (SIZE (4..8))
-- Other bits than listed above shall be discarded
BMSC-InterfaceList ::= BIT STRING {
	gmb (0)} (SIZE (1..8))
-- Other bits than listed above shall be discarded.

TraceEventList ::= SEQUENCE {
	msc-s-List	[0] MSC-S-EventList	OPTIONAL,
	mgw-List		[1] MGW-EventList	OPTIONAL,
	sgsn-List		[2] SGSN-EventList	OPTIONAL,
	ggsn-List		[3] GGSN-EventList	OPTIONAL,
	bmsc-List		[4] BMSC-EventList	OPTIONAL,
	...}
MSC-S-EventList ::= BIT STRING {
	mo-mtCall (0),
	mo-mt-sms (1),
	lu-imsiAttach-imsiDetach (2),
	handovers (3),
	ss (4)} (SIZE (5..16))
-- Other bits than listed above shall be discarded.
MGW-EventList ::= BIT STRING {
	context (0)} (SIZE (1..8))
-- Other bits than listed above shall be discarded.
SGSN-EventList ::= BIT STRING {
	pdpContext (0),
	mo-mt-sms (1),
	rau-gprsAttach-gprsDetach (2),
	mbmsContext (3)} (SIZE (4..16))
-- Other bits than listed above shall be discarded.
GGSN-EventList ::= BIT STRING {
	pdpContext (0),
	mbmsContext (1)} (SIZE (2..8))
-- Other bits than listed above shall be discarded
BMSC-EventList ::= BIT STRING {
	mbmsMulticastServiceActivation (0)} (SIZE (1..8))
-- Other bits than listed above shall be discarded.

ActivateTraceModeRes ::= SEQUENCE {
    extensionContainer  [0] ExtensionContainer  OPTIONAL,
    ...}

DeactivateTraceModeArg ::= SEQUENCE {
    imsi            [0] IMSI        OPTIONAL,
    traceReference  [1] TraceReference,
    extensionContainer  [2] ExtensionContainer  OPTIONAL,
    ...,
    traceReference2	[3] TraceReference2	OPTIONAL}

DeactivateTraceModeRes ::= SEQUENCE {
    extensionContainer  [0] ExtensionContainer  OPTIONAL,
    ...}
--not used 
--not used END
--not used  
--------------------------------------------------------------------------------
--------------------------------------------------------------------------------
--------------------------------------------------------------------------------
--[CL] 29002-560.doc 17.7.3 Call handling data types

-- Module ----------------------------------------------------------------------
--------------------------------------------------------------------------------
-- MAP CH Data Types.
--------------------------------------------------------------------------------
--------------------------------------------------------------------------------
 
--not used MAP-CH-DataTypes {
--not used    ccitt identified-organization (4) etsi (0) mobileDomain (0)
--not used    gsm-Network (1) modules (3) map-CH-DataTypes (13) version8 (8)}
--not used 
--not used DEFINITIONS
--not used 
--not used IMPLICIT TAGS
--not used 
--not used ::=
--not used 
--not used BEGIN
--not used 
--not used EXPORTS
--not used     SendRoutingInfoArg,
--not used     SendRoutingInfoRes,
--not used     ProvideRoamingNumberArg,
--not used     ProvideRoamingNumberRes,
--not used     ResumeCallHandlingArg,
--not used     ResumeCallHandlingRes,
--not used     NumberOfForwarding,
--not used     SuppressionOfAnnouncement,
--not used     CallReferenceNumber,
--not used     ProvideSIWFSNumberArg,
--not used     ProvideSIWFSNumberRes,
--not used     SIWFSSignallingModifyArg,
--not used     SIWFSSignallingModifyRes,
--not used     SetReportingStateArg,
--not used     SetReportingStateRes,
--not used     StatusReportArg,
--not used     StatusReportRes,
--not used     RemoteUserFreeArg,
--not used     RemoteUserFreeRes,
--not used     IST-AlertArg,
--not used     IST-AlertRes,
--not used     IST-CommandArg,
--not used IST-CommandRes
--not used ;
--not used 
--not used IMPORTS
--not used     SubscriberInfo,
--not used     SupportedCamelPhases,
--not used     OfferedCamel4CSIs,
--not used     CUG-Interlock,
--not used     O-CSI, 
--not used     D-CSI,
--not used     O-BcsmCamelTDPCriteriaList, 
--not used     T-BCSM-CAMEL-TDP-CriteriaList,
--not used     IST-SupportIndicator,
--not used     IST-AlertTimerValue,
--not used     T-CSI
--not used 
--not used 
--not used FROM MAP-MS-DataTypes {
--not used    ccitt identified-organization (4) etsi (0) mobileDomain (0)
--not used    gsm-Network (1) modules (3) map-MS-DataTypes (11) version8 (8)}
--not used 
--not used     ForwardingOptions,
--not used     SS-List,
--not used     CCBS-Feature
--not used FROM MAP-SS-DataTypes {
--not used    ccitt identified-organization (4) etsi (0) mobileDomain (0)
--not used    gsm-Network (1) modules (3) map-SS-DataTypes (14) version8 (8)}
--not used 
--not used     ISDN-AddressString,
--not used     ISDN-SubaddressString,
--not used     FTN-AddressString,
--not used     ExternalSignalInfo,
--not used     Ext-ExternalSignalInfo,
--not used     IMSI,
--not used     LMSI,
--not used     Ext-BasicServiceCode,
--not used     AlertingPattern,
--not used     NAEA-PreferredCI
--not used 
--not used 
--not used FROM MAP-CommonDataTypes {
--not used    ccitt identified-organization (4) etsi (0) mobileDomain (0)
--not used    gsm-Network (1) modules (3) map-CommonDataTypes (18) version8 (8)}
--not used 
--not used     ExtensionContainer
--not used FROM MAP-ExtensionDataTypes {
--not used    ccitt identified-organization (4) etsi (0) mobileDomain (0)
--not used    gsm-Network (1) modules (3) map-ExtensionDataTypes (21) version8 (8)}
--not used ;
--not used 

CUG-CheckInfo ::= SEQUENCE {
    cug-Interlock   CUG-Interlock,
    cug-OutgoingAccess  NULL            OPTIONAL,
    extensionContainer  ExtensionContainer  OPTIONAL,
    ...}

NumberOfForwarding ::= INTEGER (1..5)

SendRoutingInfoArg ::= SEQUENCE {
    msisdn      [0] ISDN-AddressString,
    cug-CheckInfo   [1] CUG-CheckInfo   OPTIONAL,
    numberOfForwarding  [2] NumberOfForwarding  OPTIONAL,
    interrogationType   [3] InterrogationType,
    or-Interrogation    [4] NULL        OPTIONAL,
    or-Capability   [5] OR-Phase    OPTIONAL,
    gmsc-OrGsmSCF-Address    [6] ISDN-AddressString,
    callReferenceNumber [7] CallReferenceNumber OPTIONAL,
    forwardingReason    [8] ForwardingReason    OPTIONAL,
    basicServiceGroup   [9] Ext-BasicServiceCode    OPTIONAL,
    networkSignalInfo   [10] ExternalSignalInfo OPTIONAL,
    camelInfo       [11] CamelInfo  OPTIONAL,
    suppressionOfAnnouncement   [12] SuppressionOfAnnouncement  OPTIONAL,
    extensionContainer  [13] ExtensionContainer OPTIONAL,
    ...,
    alertingPattern [14] AlertingPattern    OPTIONAL,
    ccbs-Call       [15] NULL           OPTIONAL,
    supportedCCBS-Phase [16]     SupportedCCBS-Phase    OPTIONAL,
    additionalSignalInfo    [17] Ext-ExternalSignalInfo OPTIONAL,
    istSupportIndicator [18] IST-SupportIndicator   OPTIONAL,
    pre-pagingSupported [19]    NULL        OPTIONAL,
    callDiversionTreatmentIndicator [20]    CallDiversionTreatmentIndicator OPTIONAL,
    longFTN-Supported   [21]    NULL        OPTIONAL,
    suppress-VT-CSI	[22]	NULL		OPTIONAL,
    suppressIncomingCallBarring	[23]	NULL		OPTIONAL,
    gsmSCF-InitiatedCall	[24]	NULL		OPTIONAL,
    basicServiceGroup2	[25] Ext-BasicServiceCode	OPTIONAL,
    networkSignalInfo2	[26] ExternalSignalInfo	OPTIONAL
 }

SuppressionOfAnnouncement ::= NULL

InterrogationType ::= ENUMERATED {
    basicCall  (0),
    forwarding  (1)}

OR-Phase ::= INTEGER (1..127)

CallReferenceNumber ::= OCTET STRING (SIZE (1..8))

ForwardingReason ::= ENUMERATED {
    notReachable  (0),
    busy  (1),
    noReply  (2)}

SupportedCCBS-Phase ::= INTEGER (1..127) 
-- exception handling:
-- Only value 1 is used.
-- Values in the ranges 2-127 are reserved for future use.
-- If received values 2-127 shall be mapped on to value 1.

CallDiversionTreatmentIndicator ::= OCTET STRING (SIZE(1))
--  callDiversionAllowed (xxxx xx01)
--  callDiversionNotAllowed (xxxx xx10)
--  network default is call diversion allowed

SendRoutingInfoRes ::= [3] SEQUENCE {
    imsi            [9] IMSI        OPTIONAL,
    -- IMSI must be present if SendRoutingInfoRes is not segmented.
    -- If the TC-Result-NL segmentation option is taken the IMSI must be
    -- present in one segmented transmission of SendRoutingInfoRes.
    extendedRoutingInfo ExtendedRoutingInfo OPTIONAL,
    cug-CheckInfo   [3] CUG-CheckInfo   OPTIONAL,
    cugSubscriptionFlag [6] NULL        OPTIONAL,
    subscriberInfo  [7] SubscriberInfo  OPTIONAL,
    ss-List     [1] SS-List OPTIONAL,
    basicService    [5] Ext-BasicServiceCode    OPTIONAL,
    forwardingInterrogationRequired [4] NULL        OPTIONAL,
    vmsc-Address    [2] ISDN-AddressString  OPTIONAL,
    extensionContainer  [0] ExtensionContainer  OPTIONAL,
    ... ,
    naea-PreferredCI    [10] NAEA-PreferredCI   OPTIONAL,
    -- naea-PreferredCI is included at the discretion of the HLR operator.
    ccbs-Indicators [11] CCBS-Indicators    OPTIONAL,
    msisdn      [12] ISDN-AddressString OPTIONAL,
    numberPortabilityStatus [13] NumberPortabilityStatus    OPTIONAL,
    istAlertTimer   [14] IST-AlertTimerValue    OPTIONAL,
    supportedCamelPhasesInVMSC	[15]	SupportedCamelPhases	OPTIONAL,
    offeredCamel4CSIsInVMSC	[16] OfferedCamel4CSIs	OPTIONAL,
    routingInfo2	[17] RoutingInfo	OPTIONAL,
	ss-List2		[18] SS-List	OPTIONAL,
	basicService2	[19] Ext-BasicServiceCode	OPTIONAL,
	allowedServices	[20] AllowedServices	OPTIONAL,
	unavailabilityCause	[21] UnavailabilityCause	OPTIONAL,
	releaseResourcesSupported	[22] NULL		OPTIONAL
 }
--atf
AllowedServices ::= BIT STRING {
	firstServiceAllowed	(0),
	secondServiceAllowed	(1) } (SIZE (2..8))
	--	firstService is the service indicated in the networkSignalInfo
	--	secondService is the service indicated in the networkSignalInfo2
	--	Other bits than listed above shall be discarded
UnavailabilityCause ::= ENUMERATED {
	bearerServiceNotProvisioned	(1),
	teleserviceNotProvisioned	(2),
	absentSubscriber	(3),
	busySubscriber	(4),
	callBarred	(5),
	cug-Reject	(6),
	...}
	--	exception handling: 
	--	Reception of other values than the ones listed shall result in the service
	--	being unavailable for that call.

--NumberPortabilityStatus ::= ENUMERATED {
 --   notKnownToBePorted  (0),
--    ownNumberPortedOut  (1),
--    foreignNumberPortedToForeignNetwork (2),
--    ...}
    --  exception handling: 
    --  reception of other values than the ones listed the receiver shall ignore the 
    --  whole NumberPortabilityStatus 

CCBS-Indicators ::= SEQUENCE {
    ccbs-Possible   [0] NULL        OPTIONAL,
    keepCCBS-CallIndicator  [1] NULL        OPTIONAL,
    extensionContainer  [2] ExtensionContainer  OPTIONAL,
    ...}

RoutingInfo ::= CHOICE {
    roamingNumber   ISDN-AddressString,
    forwardingData  ForwardingData}

ForwardingData ::= SEQUENCE {
    forwardedToNumber   [5] ISDN-AddressString  OPTIONAL,
    -- When this datatype is sent from an HLR which supports CAMEL Phase 2
    -- to a GMSC which supports CAMEL Phase 2 the GMSC shall not check the
    -- format of the number
    forwardedToSubaddress   [4] ISDN-SubaddressString   OPTIONAL,
    forwardingOptions   [6] ForwardingOptions   OPTIONAL,
    extensionContainer  [7] ExtensionContainer  OPTIONAL,
    ...,
    longForwardedToNumber   [8] FTN-AddressString   OPTIONAL}

ProvideRoamingNumberArg ::= SEQUENCE {
    imsi            [0] IMSI,
    msc-Number  [1] ISDN-AddressString,
    msisdn      [2] ISDN-AddressString  OPTIONAL,
    lmsi            [4] LMSI        OPTIONAL,
    gsm-BearerCapability    [5] ExternalSignalInfo  OPTIONAL,
    networkSignalInfo   [6] ExternalSignalInfo  OPTIONAL,
    suppressionOfAnnouncement   [7] SuppressionOfAnnouncement   OPTIONAL,
    gmsc-Address    [8] ISDN-AddressString  OPTIONAL,
    callReferenceNumber [9] CallReferenceNumber OPTIONAL,
    or-Interrogation    [10] NULL       OPTIONAL,
    extensionContainer  [11] ExtensionContainer OPTIONAL,
    ... ,
    alertingPattern [12] AlertingPattern    OPTIONAL,
    ccbs-Call       [13] NULL       OPTIONAL,
    supportedCamelPhasesInInterrogatingNode  [15] SupportedCamelPhases   OPTIONAL,
    additionalSignalInfo    [14] Ext-ExternalSignalInfo OPTIONAL,
    orNotSupportedInGMSC    [16] NULL       OPTIONAL,
    pre-pagingSupported [17] NULL       OPTIONAL,
    longFTN-Supported   [18]    NULL        OPTIONAL,
    suppress-VT-CSI	[19]	NULL		OPTIONAL,
    offeredCamel4CSIsInInterrogatingNode	[20] OfferedCamel4CSIs	OPTIONAL }

ProvideRoamingNumberRes ::= SEQUENCE {
    roamingNumber   ISDN-AddressString,
    extensionContainer  ExtensionContainer  OPTIONAL,
    ...,
    releaseResourcesSupported	NULL			OPTIONAL }

ResumeCallHandlingArg ::= SEQUENCE {
    callReferenceNumber [0] CallReferenceNumber OPTIONAL,
    basicServiceGroup   [1] Ext-BasicServiceCode    OPTIONAL,
    forwardingData  [2] ForwardingData  OPTIONAL,
    imsi            [3] IMSI        OPTIONAL,
    cug-CheckInfo   [4] CUG-CheckInfo   OPTIONAL,
    o-CSI       [5] O-CSI       OPTIONAL,
    extensionContainer  [7] ExtensionContainer  OPTIONAL,
    ccbs-Possible   [8] NULL        OPTIONAL,
    msisdn      [9] ISDN-AddressString  OPTIONAL,
    uu-Data     [10] UU-Data    OPTIONAL,
    allInformationSent  [11] NULL       OPTIONAL,
    ...,
    d-csi       [12]    D-CSI   OPTIONAL,
    o-BcsmCamelTDPCriteriaList 	[13] O-BcsmCamelTDPCriteriaList  OPTIONAL,
	basicServiceGroup2	[14] Ext-BasicServiceCode	OPTIONAL }

UU-Data ::= SEQUENCE {
    uuIndicator [0] UUIndicator OPTIONAL,
    uui         [1] UUI     OPTIONAL,
    uusCFInteraction    [2] NULL        OPTIONAL,
    extensionContainer  [3] ExtensionContainer  OPTIONAL,
    ...}

UUIndicator ::= OCTET STRING (SIZE (1))
    -- Octets are coded according to ETS 300 356

UUI  ::= OCTET STRING (SIZE (1..131))
    -- Octets are coded according to ETS 300 356

ResumeCallHandlingRes ::= SEQUENCE {
    extensionContainer  ExtensionContainer  OPTIONAL,
    ...}

CamelInfo ::= SEQUENCE {
    supportedCamelPhases    SupportedCamelPhases,
    suppress-T-CSI  NULL            OPTIONAL,
    extensionContainer  ExtensionContainer  OPTIONAL,
    ...,
    offeredCamel4CSIs	[0] OfferedCamel4CSIs	OPTIONAL }

--change for compiler 
--change for compiler ExtendedRoutingInfo ::= CHOICE {
--change for compiler     routingInfo RoutingInfo,
--change for compiler     camelRoutingInfo    [8] CamelRoutingInfo}
--change for compiler

----------------------------------------------------------------------
-- Flattened type ExtendedRoutingInfo (no more recursive CHOICE).
----------------------------------------------------------------------

ExtendedRoutingInfo ::= CHOICE {
    roamingNumber ISDN-AddressString,
    forwardingData ForwardingData,  
    camelRoutingInfo    [8] CamelRoutingInfo}

CamelRoutingInfo ::= SEQUENCE {
    forwardingData  ForwardingData  OPTIONAL,
    gmscCamelSubscriptionInfo   [0] GmscCamelSubscriptionInfo,
    extensionContainer  [1] ExtensionContainer  OPTIONAL,
    ...}

GmscCamelSubscriptionInfo ::= SEQUENCE {
    t-CSI       [0] T-CSI   OPTIONAL,
    o-CSI       [1] O-CSI   OPTIONAL,
    extensionContainer  [2] ExtensionContainer  OPTIONAL,
    ...,
    o-BcsmCamelTDP-CriteriaList [3] O-BcsmCamelTDPCriteriaList  OPTIONAL,
    t-BCSM-CAMEL-TDP-CriteriaList   [4] T-BCSM-CAMEL-TDP-CriteriaList   OPTIONAL,
    d-csi       [5] D-CSI   OPTIONAL}

ProvideSIWFSNumberArg ::= SEQUENCE {
    gsm-BearerCapability    [0] ExternalSignalInfo,
    isdn-BearerCapability   [1] ExternalSignalInfo,
    call-Direction  [2] CallDirection,
    b-Subscriber-Address    [3] ISDN-AddressString,
    chosenChannel   [4] ExternalSignalInfo,
    lowerLayerCompatibility [5] ExternalSignalInfo  OPTIONAL,
    highLayerCompatibility  [6] ExternalSignalInfo  OPTIONAL,
    extensionContainer  [7] ExtensionContainer  OPTIONAL,
    ...}

CallDirection ::= OCTET STRING (SIZE (1))
    -- OCTET 1

    -- bit 1 (direction of call)
    -- 0  Mobile Originated Call (MOC)
    -- 1  Mobile Terminated Call (MTC)

ProvideSIWFSNumberRes ::= SEQUENCE {
    sIWFSNumber [0] ISDN-AddressString,
    extensionContainer  [1] ExtensionContainer  OPTIONAL,
    ...}

SIWFSSignallingModifyArg ::= SEQUENCE {
    channelType [0] ExternalSignalInfo  OPTIONAL,
    chosenChannel   [1] ExternalSignalInfo  OPTIONAL,
    extensionContainer  [2] ExtensionContainer  OPTIONAL,
    ...}

SIWFSSignallingModifyRes ::= SEQUENCE {
    chosenChannel   [0] ExternalSignalInfo  OPTIONAL,
    extensionContainer  [1] ExtensionContainer  OPTIONAL,
    ...}

SetReportingStateArg ::= SEQUENCE {
    imsi            [0] IMSI        OPTIONAL,
    lmsi            [1] LMSI        OPTIONAL,
    ccbs-Monitoring [2] ReportingState  OPTIONAL,
    extensionContainer  [3] ExtensionContainer  OPTIONAL,
    ...}

ReportingState ::= ENUMERATED {
    stopMonitoring  (0),
    startMonitoring (1),
    ...}
    -- exception handling:
    -- reception of values 2-10 shall be mapped to 'stopMonitoring' 
    -- reception of values > 10 shall be mapped to 'startMonitoring'

SetReportingStateRes ::= SEQUENCE{
    ccbs-SubscriberStatus   [0] CCBS-SubscriberStatus   OPTIONAL,
    extensionContainer  [1] ExtensionContainer  OPTIONAL,
    ...}

CCBS-SubscriberStatus ::= ENUMERATED {
    ccbsNotIdle     (0),
    ccbsIdle        (1),
    ccbsNotReachable    (2),
    ...}
    --  exception handling: 
    --  reception of values 3-10 shall be mapped to 'ccbsNotIdle'
    --  reception of values 11-20 shall be mapped to 'ccbsIdle'
    --  reception of values > 20 shall be mapped to 'ccbsNotReachable' 

StatusReportArg ::= SEQUENCE{
    imsi        [0] IMSI,
    eventReportData [1] EventReportData OPTIONAL,
    callReportdata  [2] CallReportData  OPTIONAL,
    extensionContainer  [3] ExtensionContainer  OPTIONAL,
    ...}

EventReportData ::= SEQUENCE{
    ccbs-SubscriberStatus   [0] CCBS-SubscriberStatus   OPTIONAL,
    extensionContainer  [1] ExtensionContainer  OPTIONAL,
    ...}

CallReportData ::= SEQUENCE{
    monitoringMode  [0] MonitoringMode  OPTIONAL,
    callOutcome [1] CallOutcome OPTIONAL,
    extensionContainer  [2] ExtensionContainer  OPTIONAL,
    ...}

MonitoringMode ::= ENUMERATED {
    a-side      (0),
    b-side      (1),
    ...}
    --  exception handling: 
    --  reception of values 2-10 shall be mapped 'a-side'
    --  reception of values > 10 shall be mapped to 'b-side'

CallOutcome ::= ENUMERATED {
    success     (0),
    failure     (1),
    busy            (2),
    ...}
    --  exception handling: 
    --  reception of values 3-10 shall be mapped to 'success'
    --  reception of values 11-20 shall be mapped to 'failure'
    --  reception of values > 20 shall be mapped to 'busy'

StatusReportRes ::= SEQUENCE {
    extensionContainer  [0] ExtensionContainer  OPTIONAL,
    ...}

RemoteUserFreeArg ::= SEQUENCE{
    imsi            [0] IMSI,
    callInfo        [1] ExternalSignalInfo,
    ccbs-Feature    [2] CCBS-Feature,
    translatedB-Number  [3] ISDN-AddressString,
    replaceB-Number [4]     NULL        OPTIONAL,
    alertingPattern [5] AlertingPattern OPTIONAL,
    extensionContainer  [6] ExtensionContainer  OPTIONAL,
    ...}

RemoteUserFreeRes ::= SEQUENCE{
    ruf-Outcome [0] RUF-Outcome,
    extensionContainer  [1] ExtensionContainer  OPTIONAL,
    ...}

RUF-Outcome ::= ENUMERATED{
    accepted (0),
    rejected (1),
    noResponseFromFreeMS (2), -- T4 Expiry
    noResponseFromBusyMS (3), -- T10 Expiry
    udubFromFreeMS (4),
    udubFromBusyMS (5),
    ...}
    -- exception handling:
    -- reception of values 6-20 shall be mapped to 'accepted'
    -- reception of values 21-30 shall be mapped to 'rejected'
    -- reception of values 31-40 shall be mapped to 'noResponseFromFreeMS'
    -- reception of values 41-50 shall be mapped to 'noResponseFromBusyMS'
    -- reception of values 51-60 shall be mapped to 'udubFromFreeMS'
    -- reception of values > 60 shall be mapped to 'udubFromBusyMS'

IST-AlertArg ::= SEQUENCE{
    imsi            [0] IMSI,
    extensionContainer  [1] ExtensionContainer  OPTIONAL,
    ...}

IST-AlertRes ::= SEQUENCE{
    istAlertTimer   [0] IST-AlertTimerValue     OPTIONAL,
    istInformationWithdraw  [1] NULL        OPTIONAL,
    callTerminationIndicator    [2] CallTerminationIndicator    OPTIONAL,
    extensionContainer  [3] ExtensionContainer  OPTIONAL,
    ...}

IST-CommandArg ::= SEQUENCE{
    imsi            [0] IMSI,
    extensionContainer  [1] ExtensionContainer  OPTIONAL,
    ...}

IST-CommandRes ::= SEQUENCE{
    extensionContainer  ExtensionContainer  OPTIONAL,
    ...}

CallTerminationIndicator ::= ENUMERATED {
    terminateCallActivityReferred   (0),
    terminateAllCallActivities  (1),
    ...}
    -- exception handling:
    -- reception of values 2-10 shall be mapped to ' terminateCallActivityReferred ' 
    -- reception of values > 10 shall be mapped to ' terminateAllCallActivities '

    -- In MSCs not supporting linkage of all call activities, any value received shall
    -- be interpreted as ' terminateCallActivityReferred '
ReleaseResourcesArg ::= SEQUENCE{
	msrn			ISDN-AddressString, 
	extensionContainer	ExtensionContainer	OPTIONAL,
	...}

ReleaseResourcesRes ::= SEQUENCE{
	extensionContainer	ExtensionContainer	OPTIONAL,
	...}
--atf
--not used 
--not used END
--not used  
--------------------------------------------------------------------------------
--------------------------------------------------------------------------------
--------------------------------------------------------------------------------
--[CL] 29002-562.doc 17.7.4 Supplementary service data types

-- Module ----------------------------------------------------------------------
--------------------------------------------------------------------------------
-- MAP SS Data Types.
--------------------------------------------------------------------------------
--------------------------------------------------------------------------------

--not used  
--not used MAP-SS-DataTypes {
--not used    ccitt identified-organization (4) etsi (0) mobileDomain (0)
--not used    gsm-Network (1) modules (3) map-SS-DataTypes (14) version8 (8)}
--not used 
--not used DEFINITIONS
--not used 
--not used IMPLICIT TAGS
--not used 
--not used ::=
--not used 
--not used BEGIN
--not used 
--not used EXPORTS
--not used     RegisterSS-Arg,
--not used     SS-Info,
--not used     SS-Status,
--not used     SS-SubscriptionOption,
--not used     SS-ForBS-Code,
--not used     InterrogateSS-Res,
--not used     USSD-Arg,
--not used     USSD-Res, 
--not used     USSD-DataCodingScheme,
--not used     USSD-String,
--not used     Password,
--not used     GuidanceInfo,
--not used     SS-List,
--not used     SS-InfoList,
--not used     OverrideCategory,
--not used     CliRestrictionOption,
--not used     NoReplyConditionTime,
--not used     ForwardingOptions,
--not used     maxNumOfSS,
--not used     SS-Data,
--not used     SS-InvocationNotificationArg,
--not used     SS-InvocationNotificationRes,
--not used     CCBS-Feature,
--not used     RegisterCC-EntryArg,
--not used     RegisterCC-EntryRes,
--not used     EraseCC-EntryArg,
--not used     EraseCC-EntryRes
--not used ;
--not used 
--not used IMPORTS
--not used     AddressString,
--not used     ISDN-AddressString,
--not used     ISDN-SubaddressString,
--not used     FTN-AddressString,
--not used     IMSI,
--not used     BasicServiceCode,
--not used     AlertingPattern,
--not used     EMLPP-Priority, 
--not used     MaxMC-Bearers,
--not used     MC-Bearers,
--not used     ExternalSignalInfo
--not used 
--not used FROM MAP-CommonDataTypes {
--not used    ccitt identified-organization (4) etsi (0) mobileDomain (0)
--not used    gsm-Network (1) modules (3) map-CommonDataTypes (18) version8 (8)}
--not used 
--not used     ExtensionContainer
--not used FROM MAP-ExtensionDataTypes {
--not used    ccitt identified-organization (4) etsi (0) mobileDomain (0)
--not used    gsm-Network (1) modules (3) map-ExtensionDataTypes (21) version8 (8)}
--not used 
--not used     SS-Code
--not used FROM MAP-SS-Code {
--not used    ccitt identified-organization (4) etsi (0) mobileDomain (0)
--not used    gsm-Network (1) modules (3) map-SS-Code (15) version8 (8)}
--not used ;
--not used 

RegisterSS-Arg ::= SEQUENCE {
    ss-Code     SS-Code,
    basicService    BasicServiceCode    OPTIONAL,
    forwardedToNumber   [4] AddressString   OPTIONAL,
    forwardedToSubaddress   [6] ISDN-SubaddressString   OPTIONAL,
    noReplyConditionTime    [5] NoReplyConditionTime    OPTIONAL,
    ...,
    defaultPriority [7] EMLPP-Priority  OPTIONAL,
    nbrUser     [8] MC-Bearers  OPTIONAL,
    longFTN-Supported   [9] NULL        OPTIONAL }

NoReplyConditionTime ::= INTEGER (5..30)

SS-Info ::= CHOICE {
    forwardingInfo  [0] ForwardingInfo,
    callBarringInfo [1] CallBarringInfo,
    ss-Data     [3] SS-Data}

ForwardingInfo ::= SEQUENCE {
    ss-Code     SS-Code     OPTIONAL,
    forwardingFeatureList   ForwardingFeatureList,
    ...}

ForwardingFeatureList ::= 
    SEQUENCE SIZE (1..maxNumOfBasicServiceGroups) OF
                ForwardingFeature

ForwardingFeature ::= SEQUENCE {
    basicService    BasicServiceCode    OPTIONAL,
    ss-Status       [4] SS-Status   OPTIONAL,
    forwardedToNumber   [5] ISDN-AddressString  OPTIONAL,
    forwardedToSubaddress   [8] ISDN-SubaddressString   OPTIONAL,
    forwardingOptions   [6] ForwardingOptions   OPTIONAL,
    noReplyConditionTime    [7] NoReplyConditionTime    OPTIONAL,
    ...,
    longForwardedToNumber   [9] FTN-AddressString   OPTIONAL }

SS-Status ::= OCTET STRING (SIZE (1))

    -- bits 8765: 0000 (unused)
    -- bits 4321: Used to convey the "P bit","R bit","A bit" and "Q bit",
    --          representing supplementary service state information
    --          as defined in TS 3GPP TS 23.011 [22]

    -- bit 4: "Q bit"

    -- bit 3: "P bit"

    -- bit 2: "R bit"

    -- bit 1: "A bit"

ForwardingOptions ::= OCTET STRING (SIZE (1))

    -- bit 8: notification to forwarding party
    --  0  no notification
    --  1  notification

    -- bit 7: redirecting presentation
    --  0 no presentation  
    --  1  presentation

    -- bit 6: notification to calling party
    --  0  no notification
    --  1  notification

    -- bit 5: 0 (unused)

    -- bits 43: forwarding reason
    --  00  ms not reachable
    --  01  ms busy
    --  10  no reply
    --  11  unconditional when used in a SRI Result, 
    --      or call deflection when used in a RCH Argument
    -- bits 21: 00 (unused)

CallBarringInfo ::= SEQUENCE {
    ss-Code     SS-Code     OPTIONAL,
    callBarringFeatureList  CallBarringFeatureList,
    ...}

CallBarringFeatureList ::= SEQUENCE SIZE (1..maxNumOfBasicServiceGroups) OF
                CallBarringFeature

CallBarringFeature ::= SEQUENCE {
    basicService    BasicServiceCode    OPTIONAL,
    ss-Status   [4] SS-Status   OPTIONAL,
    ...}

SS-Data ::= SEQUENCE {
    ss-Code     SS-Code     OPTIONAL,
    ss-Status       [4] SS-Status   OPTIONAL,
    ss-SubscriptionOption   SS-SubscriptionOption   OPTIONAL,
    basicServiceGroupList   BasicServiceGroupList   OPTIONAL,
    ...,
    defaultPriority EMLPP-Priority  OPTIONAL,
    nbrUser     [5] MC-Bearers  OPTIONAL
    }

SS-SubscriptionOption ::= CHOICE {
    cliRestrictionOption    [2] CliRestrictionOption,
    overrideCategory    [1] OverrideCategory}

CliRestrictionOption ::= ENUMERATED {
    permanent  (0),
    temporaryDefaultRestricted  (1),
    temporaryDefaultAllowed  (2)}

OverrideCategory ::= ENUMERATED {
    overrideEnabled  (0),
    overrideDisabled  (1)}

SS-ForBS-Code ::= SEQUENCE {
    ss-Code     SS-Code,
    basicService    BasicServiceCode    OPTIONAL,
    ...,
    longFTN-Supported   [4] NULL        OPTIONAL }

GenericServiceInfo ::= SEQUENCE {
    ss-Status   SS-Status,
    cliRestrictionOption    CliRestrictionOption    OPTIONAL,
    ...,
    maximumEntitledPriority [0] EMLPP-Priority  OPTIONAL,
    defaultPriority [1] EMLPP-Priority  OPTIONAL,
    ccbs-FeatureList    [2] CCBS-FeatureList    OPTIONAL,
    nbrSB       [3] MaxMC-Bearers   OPTIONAL,
    nbrUser     [4] MC-Bearers  OPTIONAL,
    nbrSN       [5] MC-Bearers  OPTIONAL }

CCBS-FeatureList ::= SEQUENCE SIZE (1..maxNumOfCCBS-Requests) OF
                CCBS-Feature

maxNumOfCCBS-Requests  INTEGER ::= 5

CCBS-Feature ::= SEQUENCE {
    ccbs-Index  [0] CCBS-Index  OPTIONAL,
    b-subscriberNumber  [1] ISDN-AddressString  OPTIONAL,
    b-subscriberSubaddress  [2] ISDN-SubaddressString   OPTIONAL,
    basicServiceGroup   [3] BasicServiceCode    OPTIONAL,
    ...}

CCBS-Index  ::= INTEGER (1..maxNumOfCCBS-Requests)

InterrogateSS-Res ::= CHOICE {
    ss-Status       [0] SS-Status,
    basicServiceGroupList   [2] BasicServiceGroupList,
    forwardingFeatureList   [3] ForwardingFeatureList,
    genericServiceInfo  [4] GenericServiceInfo }

USSD-Arg ::= SEQUENCE {
    ussd-DataCodingScheme   USSD-DataCodingScheme,
    ussd-String USSD-String,
    ... ,
    alertingPattern AlertingPattern OPTIONAL,
    msisdn      [0] ISDN-AddressString  OPTIONAL }

USSD-Res ::= SEQUENCE {
    ussd-DataCodingScheme   USSD-DataCodingScheme,
    ussd-String USSD-String,
    ...}

USSD-DataCodingScheme ::= OCTET STRING (SIZE (1))
    -- The structure of the USSD-DataCodingScheme is defined by
    -- the Cell Broadcast Data Coding Scheme as described in
    -- TS 3GPP TS 23.038 [25]

USSD-String ::= OCTET STRING (SIZE (1..maxUSSD-StringLength))
    -- The structure of the contents of the USSD-String is dependent
    -- on the USSD-DataCodingScheme as described in TS 3GPP TS 23.038 [25].

maxUSSD-StringLength  INTEGER ::= 160

Password ::= NumericString
    (FROM ("0"|"1"|"2"|"3"|"4"|"5"|"6"|"7"|"8"|"9"))
    (SIZE (4))

GuidanceInfo ::= ENUMERATED {
    enterPW  (0),
    enterNewPW  (1),
    enterNewPW-Again  (2)}
    -- How this information is really delivered to the subscriber
    -- (display, announcement, ...) is not part of this
    -- specification.

SS-List ::= SEQUENCE SIZE (1..maxNumOfSS) OF
                SS-Code

maxNumOfSS  INTEGER ::= 30

SS-InfoList ::= SEQUENCE SIZE (1..maxNumOfSS) OF
                SS-Info

BasicServiceGroupList ::= SEQUENCE SIZE (1..maxNumOfBasicServiceGroups) OF
                BasicServiceCode

maxNumOfBasicServiceGroups  INTEGER ::= 13

SS-InvocationNotificationArg ::= SEQUENCE {
    imsi            [0] IMSI,
    msisdn      [1] ISDN-AddressString,
    ss-Event        [2] SS-Code,
    -- The following SS-Code values are allowed :
    -- ect      SS-Code ::= '00110001'B
    -- multiPTY SS-Code ::= '01010001'B
    -- cd       SS-Code ::= '00100100'B
    -- ccbs     SS-Code ::= '01000100'B
    ss-EventSpecification   [3] SS-EventSpecification   OPTIONAL,
    extensionContainer  [4] ExtensionContainer  OPTIONAL,
    ...,
    b-subscriberNumber  [5] ISDN-AddressString  OPTIONAL,
    ccbs-RequestState   [6] CCBS-RequestState   OPTIONAL
    }

CCBS-RequestState ::= ENUMERATED {
    request     (0),
    recall      (1),
    active      (2),
    completed   (3),
    suspended   (4),
    frozen  (5),
    deleted (6)
    }

SS-InvocationNotificationRes ::= SEQUENCE {
    extensionContainer  ExtensionContainer  OPTIONAL,
    ...
    }

SS-EventSpecification ::= SEQUENCE SIZE (1..maxEventSpecification) OF
                AddressString

maxEventSpecification  INTEGER ::= 2

RegisterCC-EntryArg ::= SEQUENCE {
    ss-Code     [0] SS-Code,
    ccbs-Data       [1] CCBS-Data   OPTIONAL,
    ...}

CCBS-Data ::= SEQUENCE {
    ccbs-Feature    [0] CCBS-Feature,
    translatedB-Number  [1] ISDN-AddressString,
    serviceIndicator    [2] ServiceIndicator    OPTIONAL,
    callInfo        [3] ExternalSignalInfo,
    networkSignalInfo   [4] ExternalSignalInfo,
    ...}

ServiceIndicator ::= BIT STRING {
    clir-invoked (0),
    camel-invoked (1)} (SIZE(2..32)) 
    -- exception handling:
    -- bits 2 to 31 shall be ignored if received and not understood

RegisterCC-EntryRes ::= SEQUENCE {
    ccbs-Feature    [0] CCBS-Feature    OPTIONAL,
    ...}

EraseCC-EntryArg ::= SEQUENCE {
    ss-Code     [0] SS-Code,
    ccbs-Index  [1] CCBS-Index  OPTIONAL,
    ...}

EraseCC-EntryRes ::= SEQUENCE {
    ss-Code     [0] SS-Code,
    ss-Status       [1] SS-Status   OPTIONAL,
    ...}
--not used 
--not used END
--not used  
--------------------------------------------------------------------------------
--------------------------------------------------------------------------------
--------------------------------------------------------------------------------
--[CL] 29002-562.doc 17.7.5 Supplementary service codes

-- Module ----------------------------------------------------------------------
--------------------------------------------------------------------------------
-- MAP SS Code.
--------------------------------------------------------------------------------
--------------------------------------------------------------------------------

--not used  
--not used MAP-SS-Code {
--not used    ccitt identified-organization (4) etsi (0) mobileDomain (0)
--not used    gsm-Network (1) modules (3) map-SS-Code (15) version8 (8)}
--not used 
--not used DEFINITIONS
--not used 
--not used ::=
--not used 
--not used BEGIN

SS-Code ::= OCTET STRING (SIZE (1))
    -- This type is used to represent the code identifying a single
    -- supplementary service, a group of supplementary services, or
    -- all supplementary services. The services and abbreviations
    -- used are defined in TS 3GPP TS 22.004. The internal structure is
    -- defined as follows:
    --
    -- bits 87654321: group (bits 8765), and specific service
    -- (bits 4321)

allSS           SS-Code ::= '00000000'B
    -- reserved for possible future use
    -- all SS

allLineIdentificationSS SS-Code ::= '00010000'B
    -- reserved for possible future use
    -- all line identification SS
clip                SS-Code ::= '00010001'B
    -- calling line identification presentation
clir                SS-Code ::= '00010010'B
    -- calling line identification restriction
colp                SS-Code ::= '00010011'B
    -- connected line identification presentation
colr                SS-Code ::= '00010100'B
    -- connected line identification restriction
mci             SS-Code ::= '00010101'B
    -- reserved for possible future use
    -- malicious call identification

allNameIdentificationSS SS-Code ::= '00011000'B
    -- all name identification SS
cnap                SS-Code ::= '00011001'B
    -- calling name presentation

    -- SS-Codes '00011010'B to '00011111'B are reserved for future 
    -- NameIdentification Supplementary Service use.

allForwardingSS SS-Code ::= '00100000'B
    -- all forwarding SS
cfu             SS-Code ::= '00100001'B
    -- call forwarding unconditional
allCondForwardingSS SS-Code ::= '00101000'B
    -- all conditional forwarding SS
cfb             SS-Code ::= '00101001'B
    -- call forwarding on mobile subscriber busy
cfnry           SS-Code ::= '00101010'B
    -- call forwarding on no reply
cfnrc           SS-Code ::= '00101011'B
    -- call forwarding on mobile subscriber not reachable 
cd              SS-Code ::= '00100100'B
    -- call deflection

allCallOfferingSS   SS-Code ::= '00110000'B
    -- reserved for possible future use
    -- all call offering SS includes also all forwarding SS
ect             SS-Code ::= '00110001'B
        -- explicit call transfer
mah             SS-Code ::= '00110010'B
    -- reserved for possible future use
    -- mobile access hunting

allCallCompletionSS SS-Code ::= '01000000'B
    -- reserved for possible future use
    -- all Call completion SS
cw              SS-Code ::= '01000001'B
    -- call waiting
hold                SS-Code ::= '01000010'B
    -- call hold
ccbs-A          SS-Code ::= '01000011'B
    -- completion of call to busy subscribers, originating side
ccbs-B          SS-Code ::= '01000100'B
    -- completion of call to busy subscribers, destination side
    -- this SS-Code is used only in InsertSubscriberData and DeleteSubscriberData
mc              SS-Code ::= '01000101'B
    -- multicall

allMultiPartySS SS-Code ::= '01010000'B
    -- reserved for possible future use
    -- all multiparty SS
multiPTY            SS-Code ::= '01010001'B
    -- multiparty

allCommunityOfInterest-SS   SS-Code ::= '01100000'B
    -- reserved for possible future use
    -- all community of interest SS
cug             SS-Code ::= '01100001'B
    -- closed user group

allChargingSS       SS-Code ::= '01110000'B
    -- reserved for possible future use
    -- all charging SS
aoci                SS-Code ::= '01110001'B
    -- advice of charge information
aocc                SS-Code ::= '01110010'B
    -- advice of charge charging

allAdditionalInfoTransferSS SS-Code ::= '10000000'B
    -- reserved for possible future use
    -- all additional information transfer SS
uus1                SS-Code ::= '10000001'B
    -- UUS1 user-to-user signalling 
uus2                SS-Code ::= '10000010'B
    -- UUS2 user-to-user signalling
uus3                SS-Code ::= '10000011'B
    -- UUS3 user-to-user signalling

allBarringSS        SS-Code ::= '10010000'B
    -- all barring SS
barringOfOutgoingCalls  SS-Code ::= '10010001'B
    -- barring of outgoing calls
baoc                SS-Code ::= '10010010'B
    -- barring of all outgoing calls
boic                SS-Code ::= '10010011'B
    -- barring of outgoing international calls
boicExHC            SS-Code ::= '10010100'B
    -- barring of outgoing international calls except those directed
    -- to the home PLMN
barringOfIncomingCalls  SS-Code ::= '10011001'B
    -- barring of incoming calls
baic                SS-Code ::= '10011010'B
    -- barring of all incoming calls
bicRoam         SS-Code ::= '10011011'B
    -- barring of incoming calls when roaming outside home PLMN
    -- Country

allPLMN-specificSS  SS-Code ::= '11110000'B
plmn-specificSS-1   SS-Code ::= '11110001'B
plmn-specificSS-2   SS-Code ::= '11110010'B
plmn-specificSS-3   SS-Code ::= '11110011'B
plmn-specificSS-4   SS-Code ::= '11110100'B
plmn-specificSS-5   SS-Code ::= '11110101'B
plmn-specificSS-6   SS-Code ::= '11110110'B
plmn-specificSS-7   SS-Code ::= '11110111'B
plmn-specificSS-8   SS-Code ::= '11111000'B
plmn-specificSS-9   SS-Code ::= '11111001'B
plmn-specificSS-A   SS-Code ::= '11111010'B
plmn-specificSS-B   SS-Code ::= '11111011'B
plmn-specificSS-C   SS-Code ::= '11111100'B
plmn-specificSS-D   SS-Code ::= '11111101'B
plmn-specificSS-E   SS-Code ::= '11111110'B
plmn-specificSS-F   SS-Code ::= '11111111'B

allCallPrioritySS   SS-Code ::= '10100000'B
    -- reserved for possible future use
    -- all call priority SS
emlpp           SS-Code ::= '10100001'B
    -- enhanced Multilevel Precedence Pre-emption (EMLPP) service

allLCSPrivacyException  SS-Code ::= '10110000'B
    -- all LCS Privacy Exception Classes
universal           SS-Code ::= '10110001'B
    -- allow location by any LCS client
callSessionRelated     SS-Code ::= '10110010'B
    -- allow location by any value added LCS client to which a call/session 
    -- is established from the target MS
callSessionUnrelated       SS-Code ::= '10110011'B
    -- allow location by designated external value added LCS clients
plmnoperator        SS-Code ::= '10110100'B
    -- allow location by designated PLMN operator LCS clients
serviceType		SS-Code ::= '10110101'B
    -- allow location by LCS clients of a designated LCS service type
allMOLR-SS      SS-Code ::= '11000000'B
    -- all Mobile Originating Location Request Classes
basicSelfLocation   SS-Code ::= '11000001'B
    -- allow an MS to request its own location
autonomousSelfLocation  SS-Code ::= '11000010'B
    -- allow an MS to perform self location without interaction
    -- with the PLMN for a predetermined period of time
transferToThirdParty    SS-Code ::= '11000011'B
    -- allow an MS to request transfer of its location to another LCS client
--not used 
--not used END
--not used  
--------------------------------------------------------------------------------
--------------------------------------------------------------------------------
--------------------------------------------------------------------------------
--[CL] 29002-562.doc 17.7.6 Short message data types

-- Module ----------------------------------------------------------------------
--------------------------------------------------------------------------------
-- MAP SM Data Types.
--------------------------------------------------------------------------------
--------------------------------------------------------------------------------
 
--not used MAP-SM-DataTypes {
--not used    ccitt identified-organization (4) etsi (0) mobileDomain (0)
--not used    gsm-Network (1) modules (3) map-SM-DataTypes (16) version8 (8)}
--not used 
--not used DEFINITIONS
--not used 
--not used IMPLICIT TAGS
--not used 
--not used ::=
--not used 
--not used BEGIN
--not used 
--not used EXPORTS
--not used     RoutingInfoForSM-Arg,
--not used     RoutingInfoForSM-Res,
--not used     MO-ForwardSM-Arg,
--not used     MO-ForwardSM-Res,
--not used     MT-ForwardSM-Arg,
--not used     MT-ForwardSM-Res,
--not used     ReportSM-DeliveryStatusArg,
--not used     ReportSM-DeliveryStatusRes,
--not used     AlertServiceCentreArg,
--not used     InformServiceCentreArg,
--not used     ReadyForSM-Arg, 
--not used     ReadyForSM-Res,
--not used     SM-DeliveryOutcome,
--not used     AlertReason
--not used     Additional-Number
--not used ;
--not used 
--not used IMPORTS
--not used     AddressString,
--not used     ISDN-AddressString,
--not used     SignalInfo,
--not used     IMSI,
--not used     LMSI
--not used FROM MAP-CommonDataTypes {
--not used    ccitt identified-organization (4) etsi (0) mobileDomain (0)
--not used    gsm-Network (1) modules (3) map-CommonDataTypes (18) version8 (8)}
--not used 
--not used     AbsentSubscriberDiagnosticSM
--not used FROM MAP-ER-DataTypes {
--not used    ccitt identified-organization (4) etsi (0) mobileDomain (0)
--not used    gsm-Network (1) modules (3) map-ER-DataTypes (17) version8 (8)}
--not used 
--not used     ExtensionContainer
--not used FROM MAP-ExtensionDataTypes {
--not used    ccitt identified-organization (4) etsi (0) mobileDomain (0)
--not used    gsm-Network (1) modules (3) map-ExtensionDataTypes (21) version8 (8)}
--not used ;


RoutingInfoForSM-Arg ::= SEQUENCE {
    msisdn      [0] ISDN-AddressString,
    sm-RP-PRI       [1] BOOLEAN,
    serviceCentreAddress    [2] AddressString,
    extensionContainer  [6] ExtensionContainer  OPTIONAL,
    ... ,
    gprsSupportIndicator    [7] NULL        OPTIONAL,
    -- gprsSupportIndicator is set only if the SMS-GMSC supports
    -- receiving of two numbers from the HLR
    sm-RP-MTI       [8] SM-RP-MTI   OPTIONAL,
    sm-RP-SMEA  [9] SM-RP-SMEA  OPTIONAL }

SM-RP-MTI ::= INTEGER (0..10)
    -- 0 SMS Deliver 
    -- 1 SMS Status Report
    -- other values are reserved for future use and shall be discarded if
    -- received


SM-RP-SMEA ::= OCTET STRING (SIZE (1..12))
    -- this parameter contains an address field which is encoded 
    -- as defined in 3GPP TS 23.040. An address field contains 3 elements :
    --      address-length
    --      type-of-address
    --      address-value


RoutingInfoForSM-Res ::= SEQUENCE {
    imsi            IMSI,
    locationInfoWithLMSI    [0] LocationInfoWithLMSI,
    extensionContainer  [4] ExtensionContainer  OPTIONAL,
    ...}

LocationInfoWithLMSI ::= SEQUENCE {
    networkNode-Number  [1] ISDN-AddressString,
    lmsi            LMSI            OPTIONAL,
    extensionContainer  ExtensionContainer  OPTIONAL,
    ...,
    gprsNodeIndicator   [5] NULL        OPTIONAL,
    -- gprsNodeIndicator is set only if the SGSN number is sent as the 
    -- Network Node Number
    additional-Number   [6] Additional-Number   OPTIONAL 
    -- NetworkNode-number can be either msc-number or sgsn-number
    }

Additional-Number ::= CHOICE {
    msc-Number  [0] ISDN-AddressString,
    sgsn-Number [1] ISDN-AddressString}
    -- additional-number can be either msc-number or sgsn-number
    -- if received networkNode-number is msc-number then the    
    -- additional number is sgsn-number 
    -- if received networkNode-number is sgsn-number then the 
    -- additional number is msc-number 

MO-ForwardSM-Arg ::= SEQUENCE {
    sm-RP-DA        SM-RP-DA,
    sm-RP-OA        SM-RP-OA,
    sm-RP-UI        SignalInfo,
    extensionContainer  ExtensionContainer  OPTIONAL,
    ... ,
    imsi            IMSI        OPTIONAL }

MO-ForwardSM-Res ::= SEQUENCE {
    sm-RP-UI        SignalInfo  OPTIONAL,
    extensionContainer  ExtensionContainer  OPTIONAL,
    ...}

MT-ForwardSM-Arg ::= SEQUENCE {
    sm-RP-DA        SM-RP-DA,
    sm-RP-OA        SM-RP-OA,
    sm-RP-UI        SignalInfo,
    moreMessagesToSend  NULL            OPTIONAL,
    extensionContainer  ExtensionContainer  OPTIONAL,
    ...}

MT-ForwardSM-Res ::= SEQUENCE {
    sm-RP-UI        SignalInfo  OPTIONAL,
    extensionContainer  ExtensionContainer  OPTIONAL,
    ...}

SM-RP-DA ::= CHOICE {
    imsi            [0] IMSI,
    lmsi            [1] LMSI,
    serviceCentreAddressDA  [4] AddressString,
    noSM-RP-DA  [5] NULL}

SM-RP-OA ::= CHOICE {
    msisdn      [2] ISDN-AddressString,
    serviceCentreAddressOA  [4] AddressString,
    noSM-RP-OA  [5] NULL}

ReportSM-DeliveryStatusArg ::= SEQUENCE {
    msisdn      ISDN-AddressString,
    serviceCentreAddress    AddressString,
    sm-DeliveryOutcome  SM-DeliveryOutcome,
    absentSubscriberDiagnosticSM    [0] AbsentSubscriberDiagnosticSM
                            OPTIONAL,
    extensionContainer  [1] ExtensionContainer  OPTIONAL,
    ...,
    gprsSupportIndicator    [2] NULL        OPTIONAL,
    -- gprsSupportIndicator is set only if the SMS-GMSC supports 
    -- handling of two delivery outcomes
    deliveryOutcomeIndicator    [3]     NULL        OPTIONAL,
    -- DeliveryOutcomeIndicator is set when the SM-DeliveryOutcome
    -- is for GPRS
    additionalSM-DeliveryOutcome    [4]     SM-DeliveryOutcome  OPTIONAL,
    -- If received, additionalSM-DeliveryOutcome is for GPRS
    -- If DeliveryOutcomeIndicator is set, then AdditionalSM-DeliveryOutcome shall be absent
    additionalAbsentSubscriberDiagnosticSM  [5]     AbsentSubscriberDiagnosticSM OPTIONAL
    -- If received additionalAbsentSubscriberDiagnosticSM is for GPRS
    -- If DeliveryOutcomeIndicator is set, then AdditionalAbsentSubscriberDiagnosticSM 
    -- shall be absent
    }

SM-DeliveryOutcome ::= ENUMERATED {
    memoryCapacityExceeded  (0),
    absentSubscriber  (1),
    successfulTransfer  (2)}

ReportSM-DeliveryStatusRes ::= SEQUENCE {
    storedMSISDN    ISDN-AddressString  OPTIONAL,
    extensionContainer  ExtensionContainer  OPTIONAL,
    ...}


AlertServiceCentreArg ::= SEQUENCE {
    msisdn      ISDN-AddressString,
    serviceCentreAddress    AddressString,
    ...}

InformServiceCentreArg ::= SEQUENCE {
    storedMSISDN    ISDN-AddressString  OPTIONAL,
    mw-Status   MW-Status   OPTIONAL,
    extensionContainer  ExtensionContainer  OPTIONAL,
    ...,
    absentSubscriberDiagnosticSM	AbsentSubscriberDiagnosticSM	OPTIONAL,
    additionalAbsentSubscriberDiagnosticSM	[0]	AbsentSubscriberDiagnosticSM	OPTIONAL }
    -- additionalAbsentSubscriberDiagnosticSM may be present only if 
    -- absentSubscriberDiagnosticSM is present.
    -- if included, additionalAbsentSubscriberDiagnosticSM is for GPRS and
    -- absentSubscriberDiagnosticSM is for non-GPRS
   

MW-Status ::= BIT STRING {
    sc-AddressNotIncluded  (0),
    mnrf-Set  (1),
    mcef-Set  (2) ,
    mnrg-Set      (3)} (SIZE (6..16))
    -- exception handling:
    -- bits 4 to 15 shall be ignored if received and not understood

ReadyForSM-Arg ::= SEQUENCE {
    imsi            [0] IMSI,
    alertReason AlertReason,
    alertReasonIndicator    NULL            OPTIONAL,
    -- alertReasonIndicator is set only when the alertReason 
    -- sent to HLR is for GPRS
    extensionContainer  ExtensionContainer  OPTIONAL,
    ...}

ReadyForSM-Res ::= SEQUENCE {
    extensionContainer  ExtensionContainer  OPTIONAL,
    ...}


AlertReason ::= ENUMERATED {
    ms-Present  (0),
    memoryAvailable  (1)}
--not used 
--not used END
--not used  

--------------------------------------------------------------------------------
--------------------------------------------------------------------------------
--------------------------------------------------------------------------------
--[CL] 29002-562.doc 17.7.7 Error data types

-- Module ----------------------------------------------------------------------
--------------------------------------------------------------------------------
-- MAP ER Data Types.
--------------------------------------------------------------------------------
--------------------------------------------------------------------------------

 
--not used MAP-ER-DataTypes {
--not used    ccitt identified-organization (4) etsi (0) mobileDomain (0)
--not used    gsm-Network (1) modules (3) map-ER-DataTypes (17) version8 (8)}
--not used 
--not used DEFINITIONS
--not used 
--not used IMPLICIT TAGS
--not used 
--not used ::=
--not used 
--not used BEGIN
--not used 
--not used EXPORTS
--not used     RoamingNotAllowedParam,
--not used     CallBarredParam,
--not used     CUG-RejectParam,
--not used     SS-IncompatibilityCause,
--not used     PW-RegistrationFailureCause,
--not used     SM-DeliveryFailureCause,
--not used     SystemFailureParam,
--not used     DataMissingParam,
--not used     UnexpectedDataParam,
--not used     FacilityNotSupParam,
--not used     OR-NotAllowedParam,
--not used     UnknownSubscriberParam,
--not used     NumberChangedParam,
--not used     UnidentifiedSubParam,
--not used     IllegalSubscriberParam,
--not used     IllegalEquipmentParam,
--not used     BearerServNotProvParam,
--not used     TeleservNotProvParam,
--not used     TracingBufferFullParam,
--not used     NoRoamingNbParam,
--not used     AbsentSubscriberParam,
--not used     BusySubscriberParam,
--not used     NoSubscriberReplyParam,
--not used     ForwardingViolationParam,
--not used     ForwardingFailedParam, 
--not used     ATI-NotAllowedParam,
--not used     SubBusyForMT-SMS-Param,
--not used     MessageWaitListFullParam,
--not used     AbsentSubscriberSM-Param,
--not used     AbsentSubscriberDiagnosticSM,
--not used     ResourceLimitationParam,
--not used     NoGroupCallNbParam,
--not used     IncompatibleTerminalParam,
--not used     ShortTermDenialParam,
--not used     LongTermDenialParam,
--not used     UnauthorizedRequestingNetwork-Param,
--not used     UnauthorizedLCSClient-Param,
--not used     PositionMethodFailure-Param,
--not used UnknownOrUnreachableLCSClient-Param,
--not used     MM-EventNotSupported-Param,
--not used     SecureTransportErrorParam,
--not used ATSI-NotAllowedParam,
--not used ATM-NotAllowedParam,
--not used IllegalSS-OperationParam,
--not used SS-NotAvailableParam,
--not used SS-SubscriptionViolationParam,
--not used InformationNotAvailableParam,
--not used TargetCellOutsideGCA-Param
--not used 
--not used 
--not used 
--not used 
--not used ;
--not used 
--not used IMPORTS
--not used     SS-Status
--not used FROM MAP-SS-DataTypes {
--not used    ccitt identified-organization (4) etsi (0) mobileDomain (0)
--not used    gsm-Network (1) modules (3) map-SS-DataTypes (14) version8 (8)}
--not used 
--not used     SignalInfo,
--not used     BasicServiceCode,
--not used     NetworkResource
--not used FROM MAP-CommonDataTypes {
--not used    ccitt identified-organization (4) etsi (0) mobileDomain (0)
--not used    gsm-Network (1) modules (3) map-CommonDataTypes (18) version8 (8)}
--not used 
--not used     SecurityHeader,
--not used     ProtectedPayload
--not used FROM MAP-ST-DataTypes {
--not used    ccitt identified-organization (4) etsi (0) mobileDomain (0)
--not used    gsm-Network (1) modules (3) map-ST-DataTypes (27) version8 (8)}
--not used 
--not used 
--not used     SS-Code
--not used FROM MAP-SS-Code {
--not used    ccitt identified-organization (4) etsi (0) mobileDomain (0)
--not used    gsm-Network (1) modules (3) map-SS-Code (15) version8 (8)}
--not used 
--not used     ExtensionContainer
--not used FROM MAP-ExtensionDataTypes {
--not used    ccitt identified-organization (4) etsi (0) mobileDomain (0)
--not used    gsm-Network (1) modules (3) map-ExtensionDataTypes (21) version8 (8)}
--not used ;

RoamingNotAllowedParam ::= SEQUENCE {
    roamingNotAllowedCause  RoamingNotAllowedCause,
    extensionContainer  ExtensionContainer  OPTIONAL,
    ...}

RoamingNotAllowedCause ::= ENUMERATED {
    plmnRoamingNotAllowed  (0),
    operatorDeterminedBarring  (3)}

CallBarredParam ::= CHOICE {
    callBarringCause    CallBarringCause,
    -- call BarringCause must not be used in version 3 and higher
    extensibleCallBarredParam   ExtensibleCallBarredParam
    -- extensibleCallBarredParam must not be used in version <3
    }

CallBarringCause ::= ENUMERATED {
    barringServiceActive  (0),
    operatorBarring  (1)}

ExtensibleCallBarredParam ::= SEQUENCE {
    callBarringCause    CallBarringCause    OPTIONAL,
    extensionContainer  ExtensionContainer  OPTIONAL,
    ... ,
    unauthorisedMessageOriginator   [1] NULL        OPTIONAL }

CUG-RejectParam ::= SEQUENCE {
    cug-RejectCause CUG-RejectCause OPTIONAL,
    extensionContainer  ExtensionContainer  OPTIONAL,
    ...}

CUG-RejectCause ::= ENUMERATED {
    incomingCallsBarredWithinCUG  (0),
    subscriberNotMemberOfCUG  (1),
    requestedBasicServiceViolatesCUG-Constraints  (5),
    calledPartySS-InteractionViolation  (7)}

SS-IncompatibilityCause ::= SEQUENCE {
    ss-Code     [1] SS-Code OPTIONAL,
    basicService    BasicServiceCode    OPTIONAL,
    ss-Status       [4] SS-Status   OPTIONAL,
    ...}

PW-RegistrationFailureCause ::= ENUMERATED {
    undetermined  (0),
    invalidFormat  (1),
    newPasswordsMismatch  (2)}


SM-EnumeratedDeliveryFailureCause ::= ENUMERATED {
    memoryCapacityExceeded  (0),
    equipmentProtocolError  (1),
    equipmentNotSM-Equipped  (2),
    unknownServiceCentre  (3),
    sc-Congestion  (4),
    invalidSME-Address  (5),
    subscriberNotSC-Subscriber  (6)}

SM-DeliveryFailureCause ::= SEQUENCE {
    sm-EnumeratedDeliveryFailureCause   SM-EnumeratedDeliveryFailureCause,
    diagnosticInfo  SignalInfo  OPTIONAL,
    extensionContainer  ExtensionContainer  OPTIONAL,
    ...}

AbsentSubscriberSM-Param ::= SEQUENCE {
    absentSubscriberDiagnosticSM    AbsentSubscriberDiagnosticSM    OPTIONAL,
    -- AbsentSubscriberDiagnosticSM can be either for non-GPRS 
    -- or for GPRS
    extensionContainer  ExtensionContainer  OPTIONAL,
    ...,
    additionalAbsentSubscriberDiagnosticSM      [0]     AbsentSubscriberDiagnosticSM    OPTIONAL }
    -- if received, additionalAbsentSubscriberDiagnosticSM 
    -- is for GPRS and absentSubscriberDiagnosticSM is 
    -- for non-GPRS

AbsentSubscriberDiagnosticSM ::= INTEGER (0..255)
    -- AbsentSubscriberDiagnosticSM values are defined in ETS 300 536 3GPP TS 23.040

SystemFailureParam ::= CHOICE {
    networkResource NetworkResource,
    -- networkResource must not be used in version 3
    extensibleSystemFailureParam    ExtensibleSystemFailureParam
    -- extensibleSystemFailureParam must not be used in version <3
    }

ExtensibleSystemFailureParam ::= SEQUENCE {
    networkResource NetworkResource OPTIONAL,
    extensionContainer  ExtensionContainer  OPTIONAL,
    ...}

DataMissingParam ::= SEQUENCE {
    extensionContainer  ExtensionContainer  OPTIONAL,
    ...}

UnexpectedDataParam ::= SEQUENCE {
    extensionContainer  ExtensionContainer  OPTIONAL,
    ...}

FacilityNotSupParam ::= SEQUENCE {
    extensionContainer  ExtensionContainer  OPTIONAL,
    ...,
    shapeOfLocationEstimateNotSupported [0]	NULL		OPTIONAL,
    neededLcsCapabilityNotSupportedInServingNode [1] NULL	OPTIONAL }

OR-NotAllowedParam ::= SEQUENCE {
    extensionContainer  ExtensionContainer  OPTIONAL,
    ...}

UnknownSubscriberParam ::= SEQUENCE {
    extensionContainer  ExtensionContainer  OPTIONAL,
    ...,
    unknownSubscriberDiagnostic UnknownSubscriberDiagnostic OPTIONAL}

UnknownSubscriberDiagnostic ::= ENUMERATED {
    imsiUnknown  (0),
    gprsSubscriptionUnknown  (1),
    ...,
    npdbMismatch  (2)}
    -- if unknown values are received in    
    -- unknownSubscriberDiagnostic they shall be discarded


NumberChangedParam ::= SEQUENCE {
    extensionContainer  ExtensionContainer  OPTIONAL,
    ...}

UnidentifiedSubParam ::= SEQUENCE {
    extensionContainer  ExtensionContainer  OPTIONAL,
    ...}

IllegalSubscriberParam ::= SEQUENCE {
    extensionContainer  ExtensionContainer  OPTIONAL,
    ...}

IllegalEquipmentParam ::= SEQUENCE {
    extensionContainer  ExtensionContainer  OPTIONAL,
    ...}

BearerServNotProvParam ::= SEQUENCE {
    extensionContainer  ExtensionContainer  OPTIONAL,
    ...}

TeleservNotProvParam ::= SEQUENCE {
    extensionContainer  ExtensionContainer  OPTIONAL,
    ...}

TracingBufferFullParam ::= SEQUENCE {
    extensionContainer  ExtensionContainer  OPTIONAL,
    ...}

NoRoamingNbParam ::= SEQUENCE {
    extensionContainer  ExtensionContainer  OPTIONAL,
    ...}

AbsentSubscriberParam ::= SEQUENCE {
    extensionContainer  ExtensionContainer  OPTIONAL,
    ...,
    absentSubscriberReason  [0] AbsentSubscriberReason  OPTIONAL}

AbsentSubscriberReason ::= ENUMERATED {
    imsiDetach (0),
    restrictedArea (1),
    noPageResponse (2),
    ... ,
    purgedMS (3)}
-- exception handling: at reception of other values than the ones listed the 
-- AbsentSubscriberReason shall be ignored. 
-- The AbsentSubscriberReason: purgedMS is defined for the Super-Charger feature 
-- (see TS 23.116). If this value is received in a Provide Roaming Number response
-- it shall be mapped to the AbsentSubscriberReason: imsiDetach in the Send Routeing
-- Information response
BusySubscriberParam ::= SEQUENCE {
    extensionContainer  ExtensionContainer  OPTIONAL,
    ...,
    ccbs-Possible   [0] NULL        OPTIONAL,
    ccbs-Busy       [1] NULL        OPTIONAL}

NoSubscriberReplyParam ::= SEQUENCE {
    extensionContainer  ExtensionContainer  OPTIONAL,
    ...}

ForwardingViolationParam ::= SEQUENCE {
    extensionContainer  ExtensionContainer  OPTIONAL,
    ...}

ForwardingFailedParam ::= SEQUENCE {
    extensionContainer  ExtensionContainer  OPTIONAL,
    ...}

ATI-NotAllowedParam ::= SEQUENCE {
    extensionContainer  ExtensionContainer  OPTIONAL,
    ...}

ATSI-NotAllowedParam ::= SEQUENCE {
    extensionContainer  ExtensionContainer  OPTIONAL,
    ...}

ATM-NotAllowedParam ::= SEQUENCE {
    extensionContainer  ExtensionContainer  OPTIONAL,
    ...}

IllegalSS-OperationParam ::= SEQUENCE {
    extensionContainer  ExtensionContainer  OPTIONAL,
    ...}

SS-NotAvailableParam ::= SEQUENCE {
    extensionContainer  ExtensionContainer  OPTIONAL,
    ...}

SS-SubscriptionViolationParam ::= SEQUENCE {
    extensionContainer  ExtensionContainer  OPTIONAL,
    ...}

InformationNotAvailableParam ::= SEQUENCE {
    extensionContainer  ExtensionContainer  OPTIONAL,
    ...}

SubBusyForMT-SMS-Param ::= SEQUENCE {
    extensionContainer  ExtensionContainer  OPTIONAL,
    ... ,
    gprsConnectionSuspended NULL            OPTIONAL }
    -- If GprsConnectionSuspended is not understood it shall 
    -- be discarded

MessageWaitListFullParam ::= SEQUENCE {
    extensionContainer  ExtensionContainer  OPTIONAL,
    ...}

ResourceLimitationParam ::= SEQUENCE {
    extensionContainer  ExtensionContainer  OPTIONAL,
    ...}

NoGroupCallNbParam ::= SEQUENCE {
    extensionContainer  ExtensionContainer  OPTIONAL,
    ...}

IncompatibleTerminalParam ::= SEQUENCE {
    extensionContainer  ExtensionContainer  OPTIONAL,
    ...}

ShortTermDenialParam ::= SEQUENCE {
    ...}

LongTermDenialParam ::= SEQUENCE {
    ...}

UnauthorizedRequestingNetwork-Param ::= SEQUENCE {
    extensionContainer  ExtensionContainer  OPTIONAL,
    ...}

UnauthorizedLCSClient-Param ::= SEQUENCE {
    unauthorizedLCSClient-Diagnostic    [0] UnauthorizedLCSClient-Diagnostic    OPTIONAL,
    extensionContainer  [1] ExtensionContainer          OPTIONAL,
    ... }

UnauthorizedLCSClient-Diagnostic ::= ENUMERATED {
    noAdditionalInformation (0),
    clientNotInMSPrivacyExceptionList (1),
    callToClientNotSetup (2),
    privacyOverrideNotApplicable (3),
    disallowedByLocalRegulatoryRequirements (4),
    ...,
    unauthorizedPrivacyClass (5),
    unauthorizedCallSessionUnrelatedExternalClient (6),
    unauthorizedCallSessionRelatedExternalClient (7) }
--  exception handling:
--  any unrecognized value shall be ignored

PositionMethodFailure-Param ::= SEQUENCE {
    positionMethodFailure-Diagnostic    [0] PositionMethodFailure-Diagnostic    OPTIONAL,
    extensionContainer  [1] ExtensionContainer          OPTIONAL,
    ... }

PositionMethodFailure-Diagnostic ::= ENUMERATED {
    congestion  (0),
    insufficientResources  (1),
    insufficientMeasurementData  (2),
    inconsistentMeasurementData  (3),
    locationProcedureNotCompleted  (4),
    locationProcedureNotSupportedByTargetMS  (5),
    qoSNotAttainable  (6),
    positionMethodNotAvailableInNetwork (7),
    positionMethodNotAvailableInLocationArea    (8),
    ... }
--  exception handling:
--  any unrecognized value shall be ignored

UnknownOrUnreachableLCSClient-Param ::= SEQUENCE {
    extensionContainer  ExtensionContainer  OPTIONAL,
    ...}

MM-EventNotSupported-Param ::= SEQUENCE {
    extensionContainer  ExtensionContainer  OPTIONAL,
    ...}


TargetCellOutsideGCA-Param ::= SEQUENCE {
    extensionContainer  ExtensionContainer  OPTIONAL,
    ...}

SecureTransportErrorParam ::= SEQUENCE {
    securityHeader  SecurityHeader,
    protectedPayload    ProtectedPayload    OPTIONAL
    }
    -- The protectedPayload carries the result of applying the security function 
    -- defined in 3G TS 33.200  to the encoding of the securely transported error 
    -- parameter

--not used 
--not used END
--not used  
--------------------------------------------------------------------------------
--------------------------------------------------------------------------------
--------------------------------------------------------------------------------
--[CL] 29002-562.doc 17.7.8 Common data types

-- Module ----------------------------------------------------------------------
--------------------------------------------------------------------------------
-- MAP Common Data Types.
--------------------------------------------------------------------------------
--------------------------------------------------------------------------------
 
--not used MAP-CommonDataTypes {
--not used    ccitt identified-organization (4) etsi (0) mobileDomain (0)
--not used    gsm-Network (1) modules (3) map-CommonDataTypes (18) version8 (8)}
--not used 
--not used DEFINITIONS
--not used 
--not used IMPLICIT TAGS
--not used 
--not used ::=
--not used 
--not used BEGIN
--not used 
--not used EXPORTS
--not used 
    -- general data types and values
--not used     AddressString,
--not used     ISDN-AddressString,
--not used     maxISDN-AddressLength,
--not used     FTN-AddressString,
--not used     ISDN-SubaddressString,
--not used     ExternalSignalInfo, 
--not used     Ext-ExternalSignalInfo, 
--not used     AccessNetworkSignalInfo,
--not used     SignalInfo,
--not used     maxSignalInfoLength,
--not used     AlertingPattern,
--not used 
    -- data types for numbering and identification
--not used     IMSI,
--not used     TMSI, 
--not used     Identity,
--not used     SubscriberId,
--not used     IMEI,
--not used     HLR-List,
--not used     LMSI,
--not used     GlobalCellId,
--not used     NetworkResource,
--not used     NAEA-PreferredCI, 
--not used     NAEA-CIC, 
--not used     ASCI-CallReference,
--not used     SubscriberIdentity,
--not used     PLMN-Id,
--not used 
    -- data types for CAMEL
--not used     CellGlobalIdOrServiceAreaIdOrLAI,
--not used 
    -- data types for subscriber management
--not used     BasicServiceCode,
--not used     Ext-BasicServiceCode,
--not used     EMLPP-Info,
--not used     EMLPP-Priority, 
--not used     MC-SS-Info,
--not used     MaxMC-Bearers,
--not used     MC-Bearers,
--not used     Ext-SS-Status,
--not used 
    -- data types for geographic location
--not used     AgeOfLocationInformation,
--not used     LCSClientExternalID,
--not used     LCSClientInternalID,
--not used     LCSServiceTypeID
--not used ;
--not used 
--not used IMPORTS
--not used     TeleserviceCode,
--not used     Ext-TeleserviceCode
--not used FROM MAP-TS-Code {
--not used    ccitt identified-organization (4) etsi (0) mobileDomain (0)
--not used    gsm-Network (1) modules (3) map-TS-Code (19) version8 (8)}
--not used 
--not used     BearerServiceCode,
--not used     Ext-BearerServiceCode
--not used FROM MAP-BS-Code {
--not used    ccitt identified-organization (4) etsi (0) mobileDomain (0)
--not used    gsm-Network (1) modules (3) map-BS-Code (20) version8 (8)}
--not used 
--not used     SS-Code
--not used FROM MAP-SS-Code {
--not used    ccitt identified-organization (4) etsi (0) mobileDomain (0)
--not used    gsm-Network (1) modules (3) map-SS-Code (15) version8 (8)}
--not used 
--not used     ExtensionContainer
--not used FROM MAP-ExtensionDataTypes {
--not used    ccitt identified-organization (4) etsi (0) mobileDomain (0)
--not used    gsm-Network (1) modules (3) map-ExtensionDataTypes (21) version8 (8)}
--not used ;
--not used 
--not used 
-- general data types

TBCD-STRING ::= OCTET STRING
    -- This type (Telephony Binary Coded Decimal String) is used to
    -- represent several digits from 0 through 9, *, #, a, b, c, two
    -- digits per octet, each digit encoded 0000 to 1001 (0 to 9),
    -- 1010 (*), 1011 (#), 1100 (a), 1101 (b) or 1110 (c); 1111 used
    -- as filler when there is an odd number of digits.

    -- bits 8765 of octet n encoding digit 2n
    -- bits 4321 of octet n encoding digit 2(n-1) +1

AddressString ::= OCTET STRING (SIZE (1..maxAddressLength))
    -- This type is used to represent a number for addressing
    -- purposes. It is composed of
    --  a)  one octet for nature of address, and numbering plan
    --      indicator.
    --  b)  digits of an address encoded as TBCD-String.

    -- a)   The first octet includes a one bit extension indicator, a
    --      3 bits nature of address indicator and a 4 bits numbering
    --      plan indicator, encoded as follows:

    -- bit 8: 1  (no extension)

    -- bits 765: nature of address indicator
    --  000  unknown
    --  001  international number
    --  010  national significant number
    --  011  network specific number
    --  100  subscriber number
    --  101  reserved
    --  110  abbreviated number
    --  111  reserved for extension

    -- bits 4321: numbering plan indicator
    --  0000  unknown
    --  0001  ISDN/Telephony Numbering Plan (Rec CCITT E.164)
    --  0010  spare
    --  0011  data numbering plan (CCITT Rec X.121)
    --  0100  telex numbering plan (CCITT Rec F.69)
    --  0101  spare
    --  0110  land mobile numbering plan (CCITT Rec E.212)
    --  0111  spare
    --  1000  national numbering plan
    --  1001  private numbering plan
    --  1111  reserved for extension

    --  all other values are reserved.

    -- b)   The following octets representing digits of an address
    --      encoded as a TBCD-STRING.

maxAddressLength  INTEGER ::= 20

ISDN-AddressString ::= 
            AddressString (SIZE (1..maxISDN-AddressLength))
    -- This type is used to represent ISDN numbers.

--change for compiler (common type with MAP V1) maxISDN-AddressLength  INTEGER ::= 9
maxISDN-AddressLength  INTEGER ::= 10

FTN-AddressString ::= 
            AddressString (SIZE (1..maxFTN-AddressLength))
    -- This type is used to represent forwarded-to numbers.

maxFTN-AddressLength  INTEGER ::= 15

ISDN-SubaddressString ::= 
            OCTET STRING (SIZE (1..maxISDN-SubaddressLength))
    -- This type is used to represent ISDN subaddresses.
    -- It is composed of
    --  a)  one octet for type of subaddress and odd/even indicator.
    --  b)  20 octets for subaddress information.

    --  a)  The first octet includes a one bit extension indicator, a
    --      3 bits type of subaddress and a one bit odd/even indicator,
    --      encoded as follows:

    --  bit 8: 1  (no extension)

    --  bits 765: type of subaddress
    --      000  NSAP (X.213/ISO 8348 AD2)
    --      010  User Specified
    --      All other values are reserved

    --  bit 4: odd/even indicator
    --      0  even number of address signals
    --      1  odd number of address signals
    --      The odd/even indicator is used when the type of subaddress
    --      is "user specified" and the coding is BCD.

    --  bits 321: 000 (unused)

    --  b) Subaddress information.
    --  The NSAP X.213/ISO8348AD2 address shall be formatted as specified
    --  by octet 4 which contains the Authority and Format Identifier
    --  (AFI). The encoding is made according to the "preferred binary
    --  encoding" as defined in X.213/ISO834AD2. For the definition
    --  of this type of subaddress, see CCITT Rec I.334.

    --  For User-specific subaddress, this field is encoded according
    --  to the user specification, subject to a maximum length of 20
    --  octets. When interworking with X.25 networks BCD coding should
    --  be applied.

maxISDN-SubaddressLength  INTEGER ::= 21

ExternalSignalInfo ::= SEQUENCE {
    protocolId  ProtocolId,
    signalInfo  SignalInfo,
    -- Information about the internal structure is given in
    -- subclause 7.6.9.
    extensionContainer  ExtensionContainer  OPTIONAL,
    -- extensionContainer must not be used in version 2
    ...}

SignalInfo ::= OCTET STRING (SIZE (1..maxSignalInfoLength))

maxSignalInfoLength  INTEGER ::= 200
    -- This NamedValue represents the theoretical maximum number of octets which is
    -- available to carry a single instance of the SignalInfo data type,
    -- without requiring segmentation to cope with the network layer service.
    -- However, the actual maximum size available for an instance of the data
    -- type may be lower, especially when other information elements
    -- have to be included in the same component.

ProtocolId ::= ENUMERATED {
    gsm-0408  (1),
    gsm-0806  (2),
    gsm-BSSMAP  (3),
    -- Value 3 is reserved and must not be used
    ets-300102-1  (4)}

Ext-ExternalSignalInfo ::= SEQUENCE {
    ext-ProtocolId  Ext-ProtocolId,
    signalInfo  SignalInfo,
    -- Information about the internal structure is given in
    -- subclause 7.6.9.10
    extensionContainer  ExtensionContainer  OPTIONAL,
    ...}

Ext-ProtocolId ::= ENUMERATED {
    ets-300356  (1),
    ... 
     }
-- exception handling:
-- For Ext-ExternalSignalInfo sequences containing this parameter with any
-- other value than the ones listed the receiver shall ignore the whole 
-- Ext-ExternalSignalInfo sequence.

AccessNetworkSignalInfo ::= SEQUENCE {
    accessNetworkProtocolId AccessNetworkProtocolId,
    signalInfo  LongSignalInfo,
    -- Information about the internal structure is given in subclause 7.6.9.1
    
    extensionContainer  ExtensionContainer  OPTIONAL,
    ...}

LongSignalInfo ::= OCTET STRING (SIZE (1..maxLongSignalInfoLength))

maxLongSignalInfoLength  INTEGER ::= 2560
    -- This Named Value represents the maximum number of octets which is available
    -- to carry a single instance of the LongSignalInfo data type using
    -- White Book SCCP with the maximum number of segments.
    -- It takes account of the octets used by the lower layers of the protocol, and
    -- other information elements which may be included in the same component.

AccessNetworkProtocolId ::= ENUMERATED {
    ts3G-48006   (1),
    ts3G-25413 (2),
    ...}
    -- exception handling:
    -- For AccessNetworkSignalInfo sequences containing this parameter with any
    -- other value than the ones listed the receiver shall ignore the whole 
    -- AccessNetworkSignalInfo sequence.

AlertingPattern ::= OCTET STRING (SIZE (1) )
    -- This type is used to represent Alerting Pattern

    --  bits 8765 : 0000 (unused)

    --  bits 43 : type of Pattern
    --      00 level
    --      01 category
    --      10 category
    --      all other values are reserved.

    --  bits 21 : type of alerting

alertingLevel-0   AlertingPattern ::= '00000000'B
alertingLevel-1   AlertingPattern ::= '00000001'B
alertingLevel-2   AlertingPattern ::= '00000010'B
    -- all other values of Alerting level are reserved
    -- Alerting Levels are defined in GSM 02.07
    
alertingCategory-1   AlertingPattern ::= '00000100'B
alertingCategory-2   AlertingPattern ::= '00000101'B
alertingCategory-3   AlertingPattern ::= '00000110'B
alertingCategory-4   AlertingPattern ::= '00000111'B
alertingCategory-5   AlertingPattern ::= '00001000'B
    -- all other values of Alerting Category are reserved
    -- Alerting categories are defined in GSM 02.07


-- data types for numbering and identification

--change for compiler (common type with MAP V1) IMSI ::= TBCD-STRING (SIZE (3..8))
IMSI ::= TBCD-STRING (SIZE (3..8))
    -- digits of MCC, MNC, MSIN are concatenated in this order.

Identity ::= CHOICE {
    imsi            IMSI,
    imsi-WithLMSI   IMSI-WithLMSI}

IMSI-WithLMSI ::= SEQUENCE {
    imsi            IMSI,
    lmsi            LMSI,
    -- a special value 00000000 indicates that the LMSI is not in use
    ...}

ASCI-CallReference ::= TBCD-STRING (SIZE (1..8))
    -- digits of VGCS/VBC-area,Group-ID are concatenated in this order.


TMSI ::= OCTET STRING (SIZE (1..4))

SubscriberId ::= CHOICE {
    imsi            [0] IMSI,
    tmsi            [1] TMSI}

IMEI ::= TBCD-STRING (SIZE (8))
    --  Refers to International Mobile Station Equipment Identity
    --  and Software Version Number (SVN) defined in TS 3GPP TS 23.003 [17].
    --  If the SVN is not present the last octet shall contain the
    --  digit 0 and a filler.
    --  If present the SVN shall be included in the last octet.

HLR-Id ::= IMSI
    -- leading digits of IMSI, i.e. (MCC, MNC, leading digits of
    -- MSIN) forming HLR Id defined in TS 3GPP TS 23.003 [17].

HLR-List ::= SEQUENCE SIZE (1..maxNumOfHLR-Id) OF
                HLR-Id

maxNumOfHLR-Id  INTEGER ::= 50

LMSI ::= OCTET STRING (SIZE (4))

GlobalCellId ::= OCTET STRING (SIZE (5..7))
    -- Refers to Cell Global Identification defined in TS 3GPP TS 23.003 [17].
    -- The internal structure is defined as follows:
    -- octet 1 bits 4321    Mobile Country Code 1st digit
    --         bits 8765    Mobile Country Code 2nd digit
    -- octet 2 bits 4321    Mobile Country Code 3rd digit
    --         bits 8765    Mobile Network Code 3rd digit
    --          or filler (1111) for 2 digit MNCs
    -- octet 3 bits 4321    Mobile Network Code 1st digit
    --         bits 8765    Mobile Network Code 2nd digit
    -- octets 4 and 5   Location Area Code according to TS 3GPP TS 24.008 [35]
    -- octets 6 and 7   Cell Identity (CI) according to TS 3GPP TS 24.008 [35]

NetworkResource ::= ENUMERATED {
    plmn  (0),
    hlr  (1),
    vlr  (2),
    pvlr  (3),
    controllingMSC  (4),
    vmsc  (5),
    eir  (6),
    rss  (7)}

AdditionalNetworkResource ::= ENUMERATED {
	sgsn (0),
	ggsn (1),
	gmlc (2),
	gsmSCF (3),
	nplr (4),
	auc (5),
	...}
	-- if unknown value is received in AdditionalNetworkResource
	-- it shall be ignored.


NAEA-PreferredCI ::= SEQUENCE {
    naea-PreferredCIC   [0] NAEA-CIC,
    extensionContainer  [1] ExtensionContainer  OPTIONAL,
    ...}

NAEA-CIC ::= OCTET STRING (SIZE (3))
    -- The internal structure is defined by the Carrier Identification
    -- parameter in ANSI T1.113.3. Carrier codes between "000" and "999" may
    -- be encoded as 3 digits using "000" to "999" or as 4 digits using 
    -- "0000" to "0999". Carrier codes between "1000" and "9999" are encoded
    -- using 4 digits.

SubscriberIdentity ::= CHOICE {
    imsi            [0] IMSI,
    msisdn      [1] ISDN-AddressString
    }

LCSClientExternalID ::= SEQUENCE {
    externalAddress [0] AddressString   OPTIONAL,
    extensionContainer  [1] ExtensionContainer  OPTIONAL,
    ... }

LCSClientInternalID ::= ENUMERATED {
    broadcastService    (0),
    o-andM-HPLMN    (1),
    o-andM-VPLMN    (2),
    anonymousLocation   (3),
    targetMSsubscribedService   (4),
    ... }
-- for a CAMEL phase 3 PLMN operator client, the value targetMSsubscribedService shall be used

LCSServiceTypeID ::= INTEGER (0..127)
    -- the integer values 0-63 are reserved for Standard LCS service types
    -- the integer values 64-127 are reserved for Non Standard LCS service types

emergencyServices		LCSServiceTypeID ::= 0
emergencyAlertServices		LCSServiceTypeID ::= 1
personTracking			LCSServiceTypeID ::= 2
fleetManagement		LCSServiceTypeID ::= 3
assetManagement		LCSServiceTypeID ::= 4
trafficCongestionReporting		LCSServiceTypeID ::= 5
roadsideAssistance		LCSServiceTypeID ::= 6
routingToNearestCommercialEnterprise		LCSServiceTypeID ::= 7
navigation			LCSServiceTypeID ::= 8
citySightseeing		LCSServiceTypeID ::= 9
localizedAdvertising		LCSServiceTypeID ::= 10
mobileYellowPages		LCSServiceTypeID ::= 11
trafficAndPublicTransportationInfo		LCSServiceTypeID ::= 12
weather				LCSServiceTypeID ::= 13
assetAndServiceFinding		LCSServiceTypeID ::= 14
gaming				LCSServiceTypeID ::= 15
findYourFriend			LCSServiceTypeID ::= 16
dating				LCSServiceTypeID ::= 17
chatting				LCSServiceTypeID ::= 18
routeFinding			LCSServiceTypeID ::= 19
whereAmI				LCSServiceTypeID ::= 20

-- The values of LCSServiceTypeID are defined according to 3GPP TS 22.071.


-- data types for CAMEL

CellGlobalIdOrServiceAreaIdOrLAI ::= CHOICE {
    cellGlobalIdOrServiceAreaIdFixedLength  [0] CellGlobalIdOrServiceAreaIdFixedLength,
    laiFixedLength  [1] LAIFixedLength}

CellGlobalIdOrServiceAreaIdFixedLength ::= OCTET STRING (SIZE (7))
    -- Refers to Cell Global Identification or Service Are Identification
    -- defined in 3G TS 23.003.
    -- The internal structure is defined as follows:
    -- octet 1 bits 4321    Mobile Country Code 1st digit
    --         bits 8765    Mobile Country Code 2nd digit
    -- octet 2 bits 4321    Mobile Country Code 3rd digit
    --         bits 8765    Mobile Network Code 3rd digit
    --          or filler (1111) for 2 digit MNCs
    -- octet 3 bits 4321    Mobile Network Code 1st digit
    --         bits 8765    Mobile Network Code 2nd digit
    -- octets 4 and 5   Location Area Code according to 3G TS 24.008
    -- octets 6 and 7   Cell Identity (CI) value or 
    --          Service Area Code (SAC) value 
    --          according to 3G TS 23.003

LAIFixedLength ::= OCTET STRING (SIZE (5))
    -- Refers to Location Area Identification defined in TS 3GPP TS 23.003 [17].
    -- The internal structure is defined as follows:
    -- octet 1 bits 4321    Mobile Country Code 1st digit
    --         bits 8765    Mobile Country Code 2nd digit
    -- octet 2 bits 4321    Mobile Country Code 3rd digit
    --         bits 8765    Mobile Network Code 3rd digit
    --          or filler (1111) for 2 digit MNCs
    -- octet 3 bits 4321    Mobile Network Code 1st digit
    --         bits 8765    Mobile Network Code 2nd digit
    -- octets 4 and 5   Location Area Code according to TS 3GPP TS 24.008 [35]


-- data types for subscriber management

BasicServiceCode ::= CHOICE {
    bearerService   [2] BearerServiceCode,
    teleservice [3] TeleserviceCode}

Ext-BasicServiceCode ::= CHOICE {
    ext-BearerService   [2] Ext-BearerServiceCode,
    ext-Teleservice [3] Ext-TeleserviceCode}

EMLPP-Info ::= SEQUENCE {
    maximumentitledPriority EMLPP-Priority,
    defaultPriority EMLPP-Priority,
    extensionContainer  ExtensionContainer  OPTIONAL,
    ...}

EMLPP-Priority ::= INTEGER (0..15)
    -- The mapping from the values A,B,0,1,2,3,4 to the integer-value is
    -- specified as follows where A is the highest and 4 is the lowest
    -- priority level
    -- the integer values 7-15 are spare and shall be mapped to value 4

priorityLevelA      EMLPP-Priority ::= 6
priorityLevelB      EMLPP-Priority ::= 5
priorityLevel0      EMLPP-Priority ::= 0
priorityLevel1      EMLPP-Priority ::= 1
priorityLevel2      EMLPP-Priority ::= 2
priorityLevel3      EMLPP-Priority ::= 3
priorityLevel4      EMLPP-Priority ::= 4


MC-SS-Info ::= SEQUENCE {
    ss-Code     [0] SS-Code,
    ss-Status       [1] Ext-SS-Status,
    nbrSB       [2] MaxMC-Bearers,
    nbrUser     [3] MC-Bearers,
    extensionContainer  [4] ExtensionContainer  OPTIONAL,
    ...}

MaxMC-Bearers ::= INTEGER (2..maxNumOfMC-Bearers)

MC-Bearers ::= INTEGER (1..maxNumOfMC-Bearers)

maxNumOfMC-Bearers  INTEGER ::= 7


Ext-SS-Status ::= OCTET STRING (SIZE (1..5))

    -- OCTET 1:
    --
    -- bits 8765: 0000 (unused)
    -- bits 4321: Used to convey the "P bit","R bit","A bit" and "Q bit",
    --          representing supplementary service state information
    --          as defined in TS 3GPP TS 23.011 [22]

    -- bit 4: "Q bit"

    -- bit 3: "P bit"

    -- bit 2: "R bit"

    -- bit 1: "A bit"

    -- OCTETS 2-5: reserved for future use. They shall be discarded if
    -- received and not understood.



    -- data types for geographic location

AgeOfLocationInformation ::= INTEGER (0..32767)
-- the value represents the elapsed time in minutes since the last
-- network contact of the mobile station (i.e. the actuality of the
-- location information).
-- value "0" indicates that the MS is currently in contact with the
--           network
-- value "32767" indicates that the location information is at least
--               32767 minutes old
--not used 
--not used END
--not used  
--------------------------------------------------------------------------------
--------------------------------------------------------------------------------
--------------------------------------------------------------------------------
--[CL] 29002-562.doc 17.7.9 Teleservice Codes

-- Module ----------------------------------------------------------------------
--------------------------------------------------------------------------------
-- MAP TS Code.
--------------------------------------------------------------------------------
--------------------------------------------------------------------------------

 
--not used MAP-TS-Code {
--not used    ccitt identified-organization (4) etsi (0) mobileDomain (0)
--not used    gsm-Network (1) modules (3) map-TS-Code (19) version8 (8)}
--not used 
--not used DEFINITIONS
--not used 
--not used ::=
--not used 
--not used BEGIN
--not used 
TeleserviceCode ::= OCTET STRING (SIZE (1))
    -- This type is used to represent the code identifying a single
    -- teleservice, a group of teleservices, or all teleservices. The
    -- services are defined in TS 22.003 [4].
    -- The internal structure is defined as follows:

    -- bits 87654321: group (bits 8765) and specific service
    -- (bits 4321)

Ext-TeleserviceCode ::= OCTET STRING (SIZE (1..5))
    -- This type is used to represent the code identifying a single
    -- teleservice, a group of teleservices, or all teleservices. The
    -- services are defined in TS GSM 22.003 [4].
    -- The internal structure is defined as follows:

    -- OCTET 1:
    -- bits 87654321: group (bits 8765) and specific service
    -- (bits 4321)

    -- OCTETS 2-5: reserved for future use. If received the
    -- Ext-TeleserviceCode shall be
    -- treated according to the exception handling defined for the
    -- operation that uses this type.

    -- Ext-TeleserviceCode includes all values defined for TeleserviceCode.


allTeleservices TeleserviceCode ::= '00000000'B

allSpeechTransmissionServices   TeleserviceCode ::= '00010000'B
telephony           TeleserviceCode ::= '00010001'B
emergencyCalls      TeleserviceCode ::= '00010010'B

allShortMessageServices TeleserviceCode ::= '00100000'B
shortMessageMT-PP   TeleserviceCode ::= '00100001'B
shortMessageMO-PP   TeleserviceCode ::= '00100010'B

allFacsimileTransmissionServices    TeleserviceCode ::= '01100000'B
facsimileGroup3AndAlterSpeech   TeleserviceCode ::= '01100001'B
automaticFacsimileGroup3    TeleserviceCode ::= '01100010'B
facsimileGroup4 TeleserviceCode ::= '01100011'B

-- The following non-hierarchical Compound Teleservice Groups
-- are defined in TS 3GPP TS 22.030:
allDataTeleservices TeleserviceCode ::= '01110000'B
    -- covers Teleservice Groups 'allFacsimileTransmissionServices'
    -- and 'allShortMessageServices'
allTeleservices-ExeptSMS    TeleserviceCode ::= '10000000'B
    -- covers Teleservice Groups 'allSpeechTransmissionServices' and
    -- 'allFacsimileTransmissionServices'
--
-- Compound Teleservice Group Codes are only used in call
-- independent supplementary service operations, i.e. they
-- are not used in InsertSubscriberData or in
-- DeleteSubscriberData messages.

allVoiceGroupCallServices   TeleserviceCode ::= '10010000'B
voiceGroupCall      TeleserviceCode ::= '10010001'B
voiceBroadcastCall  TeleserviceCode ::= '10010010'B

allPLMN-specificTS  TeleserviceCode ::= '11010000'B
plmn-specificTS-1   TeleserviceCode ::= '11010001'B
plmn-specificTS-2   TeleserviceCode ::= '11010010'B
plmn-specificTS-3   TeleserviceCode ::= '11010011'B
plmn-specificTS-4   TeleserviceCode ::= '11010100'B
plmn-specificTS-5   TeleserviceCode ::= '11010101'B
plmn-specificTS-6   TeleserviceCode ::= '11010110'B
plmn-specificTS-7   TeleserviceCode ::= '11010111'B
plmn-specificTS-8   TeleserviceCode ::= '11011000'B
plmn-specificTS-9   TeleserviceCode ::= '11011001'B
plmn-specificTS-A   TeleserviceCode ::= '11011010'B
plmn-specificTS-B   TeleserviceCode ::= '11011011'B
plmn-specificTS-C   TeleserviceCode ::= '11011100'B
plmn-specificTS-D   TeleserviceCode ::= '11011101'B
plmn-specificTS-E   TeleserviceCode ::= '11011110'B
plmn-specificTS-F   TeleserviceCode ::= '11011111'B
--not used 
--not used END
--not used  
--------------------------------------------------------------------------------
--------------------------------------------------------------------------------
--------------------------------------------------------------------------------
--[CL] 29002-562.doc 17.7.10 Bearer Service Codes

-- Module ----------------------------------------------------------------------
--------------------------------------------------------------------------------
-- MAP BS Code.
--------------------------------------------------------------------------------
--------------------------------------------------------------------------------

--not used  
--not used MAP-BS-Code {
--not used    ccitt identified-organization (4) etsi (0) mobileDomain (0)
--not used    gsm-Network (1) modules (3) map-BS-Code (20) version8 (8)}
--not used 
--not used DEFINITIONS
--not used 
--not used ::=
--not used 
--not used BEGIN

BearerServiceCode ::= OCTET STRING (SIZE (1))
    -- This type is used to represent the code identifying a single
    -- bearer service, a group of bearer services, or all bearer
    -- services. The services are defined in TS 3GPP TS 22.002 [3].
    -- The internal structure is defined as follows:
    --
    -- plmn-specific bearer services:
    -- bits 87654321: defined by the HPLMN operator

    -- rest of bearer services:
    -- bit 8: 0 (unused)
    -- bits 7654321: group (bits 7654), and rate, if applicable
    -- (bits 321)

Ext-BearerServiceCode ::= OCTET STRING (SIZE (1..5))
    -- This type is used to represent the code identifying a single
    -- bearer service, a group of bearer services, or all bearer
    -- services. The services are defined in TS 3GPP TS 22.002 [3].
    -- The internal structure is defined as follows:
    --
    -- OCTET 1:
    -- plmn-specific bearer services:
    -- bits 87654321: defined by the HPLMN operator
    --
    -- rest of bearer services:
    -- bit 8: 0 (unused)
    -- bits 7654321: group (bits 7654), and rate, if applicable
    -- (bits 321)

    -- OCTETS 2-5: reserved for future use. If received the
    -- Ext-TeleserviceCode shall be
    -- treated according to the exception handling defined for the
    -- operation that uses this type. 


    -- Ext-BearerServiceCode includes all values defined for BearerServiceCode.


allBearerServices   BearerServiceCode ::= '00000000'B

allDataCDA-Services BearerServiceCode ::= '00010000'B
dataCDA-300bps      BearerServiceCode ::= '00010001'B
dataCDA-1200bps BearerServiceCode ::= '00010010'B
dataCDA-1200-75bps  BearerServiceCode ::= '00010011'B
dataCDA-2400bps BearerServiceCode ::= '00010100'B
dataCDA-4800bps BearerServiceCode ::= '00010101'B
dataCDA-9600bps BearerServiceCode ::= '00010110'B
general-dataCDA BearerServiceCode ::= '00010111'B

allDataCDS-Services BearerServiceCode ::= '00011000'B
dataCDS-1200bps BearerServiceCode ::= '00011010'B
dataCDS-2400bps BearerServiceCode ::= '00011100'B
dataCDS-4800bps BearerServiceCode ::= '00011101'B
dataCDS-9600bps BearerServiceCode ::= '00011110'B
general-dataCDS BearerServiceCode ::= '00011111'B

allPadAccessCA-Services BearerServiceCode ::= '00100000'B
padAccessCA-300bps  BearerServiceCode ::= '00100001'B
padAccessCA-1200bps BearerServiceCode ::= '00100010'B
padAccessCA-1200-75bps  BearerServiceCode ::= '00100011'B
padAccessCA-2400bps BearerServiceCode ::= '00100100'B
padAccessCA-4800bps BearerServiceCode ::= '00100101'B
padAccessCA-9600bps BearerServiceCode ::= '00100110'B
general-padAccessCA BearerServiceCode ::= '00100111'B

allDataPDS-Services BearerServiceCode ::= '00101000'B
dataPDS-2400bps BearerServiceCode ::= '00101100'B
dataPDS-4800bps BearerServiceCode ::= '00101101'B
dataPDS-9600bps BearerServiceCode ::= '00101110'B
general-dataPDS BearerServiceCode ::= '00101111'B

allAlternateSpeech-DataCDA  BearerServiceCode ::= '00110000'B

allAlternateSpeech-DataCDS  BearerServiceCode ::= '00111000'B

allSpeechFollowedByDataCDA  BearerServiceCode ::= '01000000'B

allSpeechFollowedByDataCDS  BearerServiceCode ::= '01001000'B

-- The following non-hierarchical Compound Bearer Service
-- Groups are defined in TS 3GPP TS 22.030:
allDataCircuitAsynchronous  BearerServiceCode ::= '01010000'B
    -- covers "allDataCDA-Services", "allAlternateSpeech-DataCDA" and
    -- "allSpeechFollowedByDataCDA"
allAsynchronousServices BearerServiceCode ::= '01100000'B
    -- covers "allDataCDA-Services", "allAlternateSpeech-DataCDA",
    -- "allSpeechFollowedByDataCDA" and "allPadAccessCDA-Services"
allDataCircuitSynchronous   BearerServiceCode ::= '01011000'B
    -- covers "allDataCDS-Services", "allAlternateSpeech-DataCDS" and
    -- "allSpeechFollowedByDataCDS"
allSynchronousServices  BearerServiceCode ::= '01101000'B
    -- covers "allDataCDS-Services", "allAlternateSpeech-DataCDS",
    -- "allSpeechFollowedByDataCDS" and "allDataPDS-Services"
--
-- Compound Bearer Service Group Codes are only used in call
-- independent supplementary service operations, i.e. they
-- are not used in InsertSubscriberData or in
-- DeleteSubscriberData messages.

allPLMN-specificBS  BearerServiceCode ::= '11010000'B
plmn-specificBS-1   BearerServiceCode ::= '11010001'B
plmn-specificBS-2   BearerServiceCode ::= '11010010'B
plmn-specificBS-3   BearerServiceCode ::= '11010011'B
plmn-specificBS-4   BearerServiceCode ::= '11010100'B
plmn-specificBS-5   BearerServiceCode ::= '11010101'B
plmn-specificBS-6   BearerServiceCode ::= '11010110'B
plmn-specificBS-7   BearerServiceCode ::= '11010111'B
plmn-specificBS-8   BearerServiceCode ::= '11011000'B
plmn-specificBS-9   BearerServiceCode ::= '11011001'B
plmn-specificBS-A   BearerServiceCode ::= '11011010'B
plmn-specificBS-B   BearerServiceCode ::= '11011011'B
plmn-specificBS-C   BearerServiceCode ::= '11011100'B
plmn-specificBS-D   BearerServiceCode ::= '11011101'B
plmn-specificBS-E   BearerServiceCode ::= '11011110'B
plmn-specificBS-F   BearerServiceCode ::= '11011111'B
--not used 
--not used END
--not used  
--------------------------------------------------------------------------------
--------------------------------------------------------------------------------
--------------------------------------------------------------------------------
--[CL] 29002-562.doc 17.7.11 Extension data types

-- Module ----------------------------------------------------------------------
--------------------------------------------------------------------------------
-- MAP Extension Data Types.
--------------------------------------------------------------------------------
--------------------------------------------------------------------------------

--not used  
--not used MAP-ExtensionDataTypes {
--not used    ccitt identified-organization (4) etsi (0) mobileDomain (0)
--not used    gsm-Network (1) modules (3) map-ExtensionDataTypes (21) version8 (8)}
--not used 
--not used DEFINITIONS
--not used 
--not used IMPLICIT TAGS
--not used 
--not used ::=
--not used 
--not used BEGIN
--not used 
--not used EXPORTS
--not used 
--not used     PrivateExtension,
--not used     ExtensionContainer;
--not used 

-- IOC for private MAP extensions


--change for compiler MAP-EXTENSION  ::= CLASS {
--change for compiler     &ExtensionType              OPTIONAL,
--change for compiler     &extensionId    OBJECT IDENTIFIER }

    -- The length of the Object Identifier shall not exceed 16 octets and the
    -- number of components of the Object Identifier shall not exceed 16



-- data types

ExtensionContainer ::= SEQUENCE {
    privateExtensionList    [0]PrivateExtensionList OPTIONAL, 
    pcs-Extensions  [1]PCS-Extensions   OPTIONAL,
    ...}
SLR-ArgExtensionContainer ::= SEQUENCE {
	privateExtensionList	[0]PrivateExtensionList	OPTIONAL, 
	slr-Arg-PCS-Extensions	[1]SLR-Arg-PCS-Extensions	OPTIONAL,
	...}

PrivateExtensionList ::= SEQUENCE SIZE (1..maxNumOfPrivateExtensions) OF
                PrivateExtension

--change for compiler PrivateExtension ::= SEQUENCE {
--change for compiler     extId       MAP-EXTENSION.&extensionId
--change for compiler                 ({ExtensionSet}),
--change for compiler     extType     MAP-EXTENSION.&ExtensionType
--change for compiler                 ({ExtensionSet}{@extId})    OPTIONAL}

------------------------------------------------------------
-- Replacement for type PrivateExtension.
------------------------------------------------------------

PrivateExtension ::= SEQUENCE {
    extensionId     OBJECT IDENTIFIER,
    extensionType   ANY OPTIONAL
    }

maxNumOfPrivateExtensions  INTEGER ::= 10

--not impl ExtensionSet        MAP-EXTENSION ::=
--not impl         {...
         -- ExtensionSet is the set of all defined private extensions
--not impl     }

    -- Unsupported private extensions shall be discarded if received.


PCS-Extensions ::= SEQUENCE {
    ...}
SLR-Arg-PCS-Extensions ::= SEQUENCE {
	...,
	na-ESRK-Request	[0]	NULL		OPTIONAL }

--not used 
--not used END
--not used 
 
--------------------------------------------------------------------------------
--------------------------------------------------------------------------------
--------------------------------------------------------------------------------
--[CL] 29002-562.doc 17.7.12 Group Call data types

-- Module ----------------------------------------------------------------------
--------------------------------------------------------------------------------
-- MAP GR Data Types.
--------------------------------------------------------------------------------
--------------------------------------------------------------------------------

--not used  
--not used MAP-GR-DataTypes {
--not used    ccitt identified-organization (4) etsi (0) mobileDomain (0)
--not used    gsm-Network (1) modules (3) map-GR-DataTypes (23) version8 (8)}
--not used 
--not used DEFINITIONS
--not used 
--not used IMPLICIT TAGS
--not used 
--not used ::=
--not used 
--not used BEGIN
--not used 
--not used EXPORTS
--not used     PrepareGroupCallArg,
--not used     PrepareGroupCallRes,
--not used     SendGroupCallEndSignalArg,
--not used     SendGroupCallEndSignalRes,
--not used     ForwardGroupCallSignallingArg,
--not used     ProcessGroupCallSignallingArg
--not used ;
--not used 
--not used IMPORTS
--not used     ISDN-AddressString,
--not used     IMSI,
--not used     EMLPP-Priority,
--not used     ASCI-CallReference
--not used FROM MAP-CommonDataTypes {
--not used    ccitt identified-organization (4) etsi (0) mobileDomain (0)
--not used    gsm-Network (1) modules (3) map-CommonDataTypes (18) version8 (8)}
--not used 
--not used     Ext-TeleserviceCode
--not used FROM MAP-TS-Code {
--not used    ccitt identified-organization (4) etsi (0) mobileDomain (0)
--not used    gsm-Network (1) modules (3) map-TS-Code (19) version8 (8)}
--not used 
--not used     Kc
--not used FROM MAP-MS-DataTypes {
--not used    ccitt identified-organization (4) etsi (0) mobileDomain (0)
--not used    gsm-Network (1) modules (3) map-MS-DataTypes (11) version8 (8)}
--not used 
--not used 
--not used     ExtensionContainer
--not used FROM MAP-ExtensionDataTypes {
--not used    ccitt identified-organization (4) etsi (0) mobileDomain (0)
--not used    gsm-Network (1) modules (3) map-ExtensionDataTypes (21) version8 (8)}
--not used ;


PrepareGroupCallArg ::= SEQUENCE {
    teleservice Ext-TeleserviceCode,
    asciCallReference   ASCI-CallReference,
    codec-Info  CODEC-Info,
    cipheringAlgorithm  CipheringAlgorithm,
    groupKeyNumber  [0]GroupKeyNumber   OPTIONAL,
    groupKey        [1]Kc       OPTIONAL,
    priority        [2]EMLPP-Priority   OPTIONAL,
    uplinkFree  [3] NULL        OPTIONAL,
    extensionContainer  [4] ExtensionContainer  OPTIONAL,
    ...,
    vstk		[5] VSTK		OPTIONAL,
    vstk-rand		[6] VSTK-RAND
}
VSTK ::= OCTET STRING (SIZE (16))
VSTK-RAND ::= OCTET STRING (SIZE (5))
	-- The 36 bit value is carried in bit 7 of octet 1 to bit 4 of octet 5
	-- bits 3, 2, 1, and 0 of octet 5 are padded with zeros.

PrepareGroupCallRes ::= SEQUENCE {
    groupCallNumber ISDN-AddressString,
    extensionContainer  ExtensionContainer  OPTIONAL,
    ...}

SendGroupCallEndSignalArg ::= SEQUENCE {
    imsi            IMSI            OPTIONAL,
    extensionContainer  ExtensionContainer  OPTIONAL,
    ...}

SendGroupCallEndSignalRes ::= SEQUENCE {
    extensionContainer  ExtensionContainer  OPTIONAL,
    ...}

ForwardGroupCallSignallingArg ::= SEQUENCE {
    imsi            IMSI            OPTIONAL,
    uplinkRequestAck    [0] NULL        OPTIONAL,
    uplinkReleaseIndication [1] NULL        OPTIONAL,
    uplinkRejectCommand [2] NULL        OPTIONAL,
    uplinkSeizedCommand [3] NULL        OPTIONAL,
    uplinkReleaseCommand    [4] NULL        OPTIONAL,
    extensionContainer  ExtensionContainer  OPTIONAL,
    ..., 
    stateAttributes [5] StateAttributes OPTIONAL }

ProcessGroupCallSignallingArg ::= SEQUENCE {
    uplinkRequest   [0] NULL        OPTIONAL,
    uplinkReleaseIndication [1] NULL        OPTIONAL,
    releaseGroupCall    [2] NULL        OPTIONAL,
    extensionContainer  ExtensionContainer  OPTIONAL,
    ...}

GroupKeyNumber ::= INTEGER (0..15)

CODEC-Info ::= OCTET STRING (SIZE (5..10))
    -- Refers to channel type
    -- coded according to 3GPP TS 48.008 [49] and including Element identifier and Length 


CipheringAlgorithm ::= OCTET STRING (SIZE (1))
    -- Refers to 'permitted algorithms' in 'encryption information'
    -- coded according to 3GPP TS 48.008 [49]:
    
    -- Bits 8-1 
    -- 8765 4321
    -- 0000 0001    No encryption
    -- 0000 0010    GSM A5/1
    -- 0000 0100    GSM A5/2
    -- 0000 1000    GSM A5/3
    -- 0001 0000    GSM A5/4
    -- 0010 0000    GSM A5/5
    -- 0100 0000    GSM A5/6
    -- 1000 0000    GSM A5/7




StateAttributes ::= SEQUENCE {
    downlinkAttached            [5] NULL        OPTIONAL,
    uplinkAttached          [6] NULL        OPTIONAL,
    dualCommunication           [7] NULL        OPTIONAL,
    callOriginator          [8] NULL        OPTIONAL }

    -- Refers to 3GPP TS 44.068 for definitions of StateAttributes fields. 

--not used 
--not used 
--not used END
--not used  

--------------------------------------------------------------------------------
--------------------------------------------------------------------------------
--------------------------------------------------------------------------------
--[CL] 29002-562.doc Location service data types

-- Module ----------------------------------------------------------------------
--------------------------------------------------------------------------------
-- MAP LCS Data Types.
--------------------------------------------------------------------------------
--------------------------------------------------------------------------------


--not used  
--not used MAP-LCS-DataTypes {
--not used    ccitt identified-organization (4) etsi (0) mobileDomain (0)
--not used    gsm-Network (1) modules (3) map-LCS-DataTypes (25) version8 (8)}
--not used 
--not used DEFINITIONS
--not used IMPLICIT TAGS
--not used ::=
--not used BEGIN
--not used 
--not used EXPORTS
--not used     RoutingInfoForLCS-Arg,
--not used     RoutingInfoForLCS-Res,
--not used     ProvideSubscriberLocation-Arg,
--not used     ProvideSubscriberLocation-Res,
--not used     SubscriberLocationReport-Arg,
--not used     SubscriberLocationReport-Res,
--not used LocationType,
--not used LCSClientName,
--not used LCS-QoS,
--not used Horizontal-Accuracy,
--not used ResponseTime,
--not used Ext-GeographicalInformation,
--not used SupportedGADShapes,
--not used Add-GeographicalInformation,
--not used LCSRequestorID,
--not used LCSCodeword

--not used ;
--not used 
--not used IMPORTS
--not used     AddressString,
--not used     ISDN-AddressString,
--not used     IMEI,
--not used     IMSI,
--not used     LMSI,
--not used     SubscriberIdentity,
--not used     AgeOfLocationInformation,
--not used     LCSClientExternalID,
--not used     LCSClientInternalID,
--not used     LCSServiceTypeID
--not used FROM MAP-CommonDataTypes {
--not used    ccitt identified-organization (4) etsi (0) mobileDomain (0)
--not used    gsm-Network (1) modules (3) map-CommonDataTypes (18) version8 (8)}
--not used 
--not used     ExtensionContainer
--not used FROM MAP-ExtensionDataTypes {
--not used    ccitt identified-organization (4) etsi (0) mobileDomain (0)
--not used    gsm-Network (1) modules (3) map-ExtensionDataTypes (21) version8 (8)}
--not used 
--not used     USSD-DataCodingScheme,
--not used USSD-String
--not used FROM MAP-SS-DataTypes {
--not used    ccitt identified-organization (4) etsi (0) mobileDomain (0) gsm-Network (1) modules (3)
--not used    map-SS-DataTypes (14) version8 (8)}
--not used     APN
--not used FROM MAP-MS-DataTypes {
--not used   itu-t identified-organization (4) etsi (0) mobileDomain (0)
--not used   gsm-Network (1) modules (3) map-MS-DataTypes (11) version8 (8)}
--not used
--not used   Additional-Number
--not used FROM MAP-SM-DataTypes {
--not used   itu-t identified-organization (4) etsi (0) mobileDomain (0)
--not used   gsm-Network (1) modules (3) map-SM-DataTypes (16) version8 (8)}
--not used ;


RoutingInfoForLCS-Arg ::= SEQUENCE {
    mlcNumber       [0] ISDN-AddressString,
    targetMS        [1] SubscriberIdentity,
    extensionContainer  [2] ExtensionContainer  OPTIONAL,
    ...}

RoutingInfoForLCS-Res ::= SEQUENCE {
    targetMS        [0] SubscriberIdentity,
    lcsLocationInfo [1] LCSLocationInfo,
    extensionContainer  [2] ExtensionContainer  OPTIONAL,
    ...,
    v-gmlc-Address	[3]	GSN-Address	OPTIONAL,
	h-gmlc-Address	[4]	GSN-Address	OPTIONAL,
	ppr-Address	[5]	GSN-Address	OPTIONAL,
	additional-v-gmlc-Address	[6]	GSN-Address	OPTIONAL
}

LCSLocationInfo ::= SEQUENCE {
    networkNode-Number  ISDN-AddressString,
    -- NetworkNode-number can be either msc-number or sgsn-number
    lmsi            [0] LMSI        OPTIONAL,
    extensionContainer  [1] ExtensionContainer  OPTIONAL,
    ...,
    gprsNodeIndicator 	[2] NULL		OPTIONAL,
    -- gprsNodeIndicator is set only if the SGSN number is sent as the Network 
    -- Node Number
    additional-Number	[3] Additional-Number	OPTIONAL,
 supportedLCS-CapabilitySets [4] SupportedLCS-CapabilitySets OPTIONAL,
 additional-LCS-CapabilitySets [5] SupportedLCS-CapabilitySets	OPTIONAL
 }

ProvideSubscriberLocation-Arg ::= SEQUENCE {
    locationType    LocationType,
    mlc-Number  ISDN-AddressString,
    lcs-ClientID    [0] LCS-ClientID    OPTIONAL,
    privacyOverride [1] NULL        OPTIONAL,
    imsi            [2] IMSI        OPTIONAL,
    msisdn      [3] ISDN-AddressString  OPTIONAL,
    lmsi            [4] LMSI        OPTIONAL,
    imei            [5] IMEI        OPTIONAL,
    lcs-Priority    [6] LCS-Priority    OPTIONAL,
    lcs-QoS     [7] LCS-QoS OPTIONAL,
    extensionContainer  [8] ExtensionContainer  OPTIONAL,
    ...,
    supportedGADShapes	[9]	SupportedGADShapes	OPTIONAL,
    lcs-ReferenceNumber	[10]	LCS-ReferenceNumber	OPTIONAL,
    lcsServiceTypeID	[11]	LCSServiceTypeID	OPTIONAL,
    lcsCodeword	[12]	LCSCodeword	OPTIONAL ,
    lcs-PrivacyCheck	[13]	LCS-PrivacyCheck	OPTIONAL,
    areaEventInfo	[14]	AreaEventInfo	OPTIONAL,
    h-gmlc-Address	[15]	GSN-Address	OPTIONAL }

    -- one of imsi or msisdn is mandatory
    -- If a location estimate type indicates activate deferred location or 
    -- cancel deferred location, a lcs-Reference number shall be included.


LocationType ::= SEQUENCE {
    locationEstimateType    [0] LocationEstimateType,
    ...,
    deferredLocationEventType	[1] DeferredLocationEventType	OPTIONAL }

LocationEstimateType ::= ENUMERATED {
    currentLocation (0),
    currentOrLastKnownLocation  (1),
    initialLocation (2),
    ...,
    activateDeferredLocation	(3),
    cancelDeferredLocation	(4) }
--  exception handling:
--  a ProvideSubscriberLocation-Arg containing an unrecognized LocationEstimateType
--  shall be rejected by the receiver with a return error cause of unexpected data value

DeferredLocationEventType ::= BIT STRING {
	msAvailable	 (0) ,
        enteringIntoArea (1),
	leavingFromArea	 (2),
	beingInsideArea	 (3)
} (SIZE (1..16)) 
-- beingInsideArea is always treated as oneTimeEvent regardless of the possible value
-- of occurrenceInfo inside areaEventInfo.
-- exception handling
-- a ProvideSubscriberLocation-Arg containing other values than listed above in 
-- DeferredLocationEventType shall be rejected by the receiver with a return error cause of 
-- unexpected data value.


LCS-ClientID ::= SEQUENCE {
    lcsClientType   [0] LCSClientType,
    lcsClientExternalID [1] LCSClientExternalID OPTIONAL,
    lcsClientDialedByMS [2] AddressString   OPTIONAL,
    lcsClientInternalID [3] LCSClientInternalID OPTIONAL,
    lcsClientName   [4] LCSClientName   OPTIONAL,
    ...,
    lcsAPN		[5] APN		OPTIONAL,
    lcsRequestorID	[6] LCSRequestorID	OPTIONAL }

LCSClientType ::= ENUMERATED {
    emergencyServices   (0),
    valueAddedServices  (1),
    plmnOperatorServices    (2),
    lawfulInterceptServices (3),
    ... }
    --  exception handling:
    --  unrecognized values may be ignored if the LCS client uses the privacy override
    --  otherwise, an unrecognized value shall be treated as unexpected data by a receiver
    --  a return error shall then be returned if received in a MAP invoke 

LCSClientName ::= SEQUENCE {
    dataCodingScheme    [0] USSD-DataCodingScheme,
    nameString  [2] NameString,
    ...,
    lcs-FormatIndicator	[3] LCS-FormatIndicator	OPTIONAL }

-- The USSD-DataCodingScheme shall indicate use of the default alphabet through the
-- following encoding
--  bit 7 6 5 4 3 2 1 0
--      0 0 0 0 1 1 1 1

NameString ::= USSD-String (SIZE (1..maxNameStringLength))

maxNameStringLength  INTEGER ::= 63

LCSRequestorID ::= SEQUENCE {
    dataCodingScheme	[0] USSD-DataCodingScheme,
    requestorIDString	[1] RequestorIDString,
    ...}

RequestorIDString ::= USSD-String (SIZE (1..maxRequestorIDStringLength))

maxRequestorIDStringLength  INTEGER ::= 63
LCS-FormatIndicator ::= ENUMERATED {
	logicalName	(0),
	e-mailAddress	(1),
	msisdn		(2),
	url			(3),
	sipUrl		(4),
	... }


LCS-Priority ::= OCTET STRING (SIZE (1))
    -- 0 = highest priority
    -- 1 = normal priority
    -- all other values treated as 1 

LCS-QoS ::= SEQUENCE {
    horizontal-accuracy [0] Horizontal-Accuracy OPTIONAL,
    verticalCoordinateRequest   [1] NULL        OPTIONAL,
    vertical-accuracy   [2] Vertical-Accuracy   OPTIONAL,   responseTime    [3] ResponseTime    OPTIONAL,
    extensionContainer  [4] ExtensionContainer  OPTIONAL,
    ...}

Horizontal-Accuracy ::= OCTET STRING (SIZE (1))
    -- bit 8 = 0
    -- bits 7-1 = 7 bit Uncertainty Code defined in 3GPP TS 23.032. The horizontal location 
    -- error should be less than the error indicated by the uncertainty code with 67%
    -- confidence.

Vertical-Accuracy ::= OCTET STRING (SIZE (1))
    -- bit 8 = 0
    -- bits 7-1 = 7 bit Vertical Uncertainty Code defined in GSM 3GPP TS 23.032. The vertical location
    -- error should be less than the error indicated by the uncertainty code with 67%
    -- confidence.

ResponseTime ::= SEQUENCE {
    responseTimeCategory    ResponseTimeCategory,
    ...}
--  note: an expandable SEQUENCE simplifies later addition of a numeric response time.

ResponseTimeCategory ::= ENUMERATED {
    lowdelay  (0),
    delaytolerant  (1),
    ... }
--  exception handling:
--  an unrecognized value shall be treated the same as value 1 (delaytolerant)

SupportedGADShapes ::= BIT STRING {
    ellipsoidPoint  (0),
    ellipsoidPointWithUncertaintyCircle (1),
    ellipsoidPointWithUncertaintyEllipse (2),
    polygon (3),
    ellipsoidPointWithAltitude (4),
    ellipsoidPointWithAltitudeAndUncertaintyElipsoid (5),
    ellipsoidArc  (6) } (SIZE (7..16))
    -- A node shall mark in the BIT STRING all Shapes defined in 3GPP TS 23.032 
    -- it supports.
    -- exception handling: bits 7 to 15 shall be ignored if received.

LCS-ReferenceNumber::= OCTET STRING (SIZE(1))

LCSCodeword ::= SEQUENCE {
    dataCodingScheme	[0] USSD-DataCodingScheme,
    lcsCodewordString	[1] LCSCodewordString,
    ...}

LCSCodewordString ::= USSD-String (SIZE (1..maxLCSCodewordStringLength))

maxLCSCodewordStringLength  INTEGER ::= 20
LCS-PrivacyCheck ::= SEQUENCE {
    callSessionUnrelated	[0] PrivacyCheckRelatedAction,
    callSessionRelated	[1] PrivacyCheckRelatedAction	OPTIONAL,
	...}
AreaEventInfo ::= SEQUENCE {
	areaDefinition	[0]	AreaDefinition,
	occurrenceInfo	[1]	OccurrenceInfo	OPTIONAL,
	intervalTime	[2]	IntervalTime	OPTIONAL,
	...}
AreaDefinition ::= SEQUENCE {
	areaList		[0]	AreaList,
	...}
AreaList ::= SEQUENCE SIZE (1..maxNumOfAreas) OF Area

maxNumOfAreas  INTEGER ::= 10

Area ::= SEQUENCE {
	areaType		[0]	AreaType,
	areaIdentification	[1]	AreaIdentification,
	...}
AreaType ::= ENUMERATED {
	countryCode	(0),
	plmnId		(1),
	locationAreaId	(2),
	routingAreaId	(3),
	cellGlobalId	(4),
	... ,
	utranCellId	(5) }
AreaIdentification ::= OCTET STRING (SIZE (2..7))
	-- The internal structure is defined as follows:
	-- octet 1 bits 4321	Mobile Country Code 1st digit
	--         bits 8765	Mobile Country Code 2nd digit
	-- octet 2 bits 4321	Mobile Country Code 3rd digit
	--         bits 8765	Mobile Network Code 3rd digit if 3 digit MNC included
	--			or filler (1111)
	-- octet 3 bits 4321	Mobile Network Code 1st digit
	--         bits 8765	Mobile Network Code 2nd digit
	-- octets 4 and 5	Location Area Code (LAC) for Local Area Id,
	--			Routing Area Id and Cell Global Id
	-- octet 6	Routing Area Code (RAC) for Routing Area Id
	-- octets 6 and 7	Cell Identity (CI) for Cell Global Id
	-- octets 4 until 7	Utran Cell Identity (UC-Id) for Utran Cell Id

OccurrenceInfo ::= ENUMERATED {
	oneTimeEvent	(0),
	multipleTimeEvent	(1),
	...}
IntervalTime ::= INTEGER (1..32767)
	-- minimum interval time between area reports in seconds


PrivacyCheckRelatedAction ::= ENUMERATED {
	allowedWithoutNotification (0),
	allowedWithNotification (1),
	allowedIfNoResponse (2),
	restrictedIfNoResponse (3),
	notAllowed (4),
	...}
--	exception handling:
--	a ProvideSubscriberLocation-Arg containing an unrecognized PrivacyCheckRelatedAction
--	shall be rejected by the receiver with a return error cause of unexpected data value


ProvideSubscriberLocation-Res ::= SEQUENCE {
    locationEstimate    Ext-GeographicalInformation,
    ageOfLocationEstimate   [0] AgeOfLocationInformation    OPTIONAL,
    extensionContainer  [1] ExtensionContainer  OPTIONAL,
    ...,
    add-LocationEstimate	[2] Add-GeographicalInformation 	OPTIONAL,
    deferredmt-lrResponseIndicator	[3] NULL		OPTIONAL,
    geranPositioningData	[4] PositioningDataInformation	OPTIONAL,
    utranPositioningData	[5] UtranPositioningDataInfo	OPTIONAL,
    cellIdOrSai	[6] CellGlobalIdOrServiceAreaIdOrLAI	OPTIONAL,
    sai-Present	[7] NULL		OPTIONAL,
    accuracyFulfilmentIndicator	[8] AccuracyFulfilmentIndicator	OPTIONAL }
--if deferredmt-lrResponseIndicator is set, locationEstimate is ignored.

-- the add-LocationEstimate parameter shall not be sent to a node that did not indicate the
-- geographic shapes supported in the ProvideSubscriberLocation-Arg
-- The locationEstimate and the add-locationEstimate parameters shall not be sent if
-- the supportedGADShapes parameter has been received in ProvideSubscriberLocation-Arg
-- and the shape encoded in locationEstimate or add-LocationEstimate is not marked
-- as supported in supportedGADShapes. In such a case ProvideSubscriberLocation
-- shall be rejected with error FacilityNotSupported with additional indication
-- shapeOfLocationEstimateNotSupported.
-- sai-Present indicates that the cellIdOrSai parameter contains a Service Area Identity.

AccuracyFulfilmentIndicator ::= ENUMERATED {
	requestedAccuracyFulfilled  (0),
	requestedAccuracyNotFulfilled  (1),
	...	}
Ext-GeographicalInformation ::= OCTET STRING (SIZE (1..maxExt-GeographicalInformation))
    -- Refers to geographical Information defined in 3GPP TS 23.032.
    -- This is composed of 1 or more octets with an internal structure according to 3GPP TS 23.032
    -- Octet 1: Type of shape, only the following shapes in 3GPP TS 23.032 are allowed:
    --      (a) Ellipsoid point with uncertainty circle
    --      (b) Ellipsoid point with uncertainty ellipse
    --      (c) Ellipsoid point with altitude and uncertainty ellipsoid
    --      (d) Ellipsoid Arc
    --	    (e) Ellipsoid Point
    -- Any other value in octet 1 shall be treated as invalid
    -- Octets 2 to 8 for case (a) - Ellipsoid point with uncertainty circle
    --      Degrees of Latitude             3 octets
    --      Degrees of Longitude                3 octets
    --      Uncertainty code                1 octet
    -- Octets 2 to 11 for case (b) - Ellipsoid point with uncertainty ellipse:
    --      Degrees of Latitude             3 octets
    --      Degrees of Longitude                3 octets
    --      Uncertainty semi-major axis             1 octet
    --      Uncertainty semi-minor axis             1 octet
    --      Angle of major axis             1 octet
    --      Confidence              1 octet
    -- Octets 2 to 14 for case (c) - Ellipsoid point with altitude and uncertainty ellipsoid
    --      Degrees of Latitude             3 octets
    --      Degrees of Longitude                3 octets
    --      Altitude                2 octets
    --      Uncertainty semi-major axis             1 octet
    --      Uncertainty semi-minor axis             1 octet
    --      Angle of major axis             1 octet
    --      Uncertainty altitude                1 octet
    --      Confidence              1 octet
    -- Octets 2 to 13 for case (d) - Ellipsoid Arc
    --      Degrees of Latitude             3 octets
    --      Degrees of Longitude                3 octets
    --      Inner radius                2 octets
    --      Uncertainty radius              1 octet
    --      Offset angle                1 octet
    --      Included angle              1 octet
    --      Confidence              1 octet
    --  Octets 2 to 7 for case (e) – Ellipsoid Point
    --	Degrees of Latitude				3 octets
    --	Degrees of Longitude				3 octets


    --
   -- An Ext-GeographicalInformation parameter comprising more than one octet 
    -- and containing any other shape or an incorrect number of octets or coding 
    -- according to 3GPP TS 23.032 shall be treated as invalid data by a 
    -- receiver.
    --
    -- An Ext-GeographicalInformation parameter comprising one octet shall be 
    -- discarded by the receiver if an Add-GeographicalInformation parameter is 
    -- received in the same message.
    --
    -- An Ext-GeographicalInformation parameter comprising one octet shall be 
    -- treated as invalid data by the receiver if an Add-GeographicalInformation 
    -- parameter is not received in the same message.


-- Ajay below is a redefinition
--maxExt-GeographicalInformation  INTEGER ::= 20
    -- the maximum length allows for further shapes in GSM 03.32 to be included in later 
    -- versions of 3GPP TS 29.002

maxExt-GeographicalInformation  INTEGER ::= 20
    -- the maximum length allows for further shapes in 3GPP TS 23.032 to be 
    -- included in later versions of 3GPP TS 29.002

PositioningDataInformation ::= OCTET STRING (SIZE (2..maxPositioningDataInformation))
    -- Refers to the Positioning Data defined in 3GPP TS 49.031.
    -- This is composed of 2 or more octets with an internal structure according 
    -- to 3GPP TS 49.031.

maxPositioningDataInformation INTEGER ::= 10
    -- 
UtranPositioningDataInfo ::= OCTET STRING (SIZE (3..maxUtranPositioningDataInfo))
	-- Refers to the Position Data defined in 3GPP TS 25.413.
	-- This is composed of the positioningDataDiscriminator and the positioningDataSet
	-- included in positionData as defined in 3GPP TS 25.413.

maxUtranPositioningDataInfo INTEGER ::= 11

Add-GeographicalInformation ::= OCTET STRING (SIZE (1..maxAdd-GeographicalInformation))
    -- Refers to geographical Information defined in 3GPP TS 23.032.
    -- This is composed of 1 or more octets with an internal structure according 
    -- to 3GPP TS 23.032
    -- Octet 1: Type of shape, all the shapes defined in 3GPP TS 23.032 are allowed:
    -- Octets 2 to n (where n is the total number of octets necessary to encode 
    -- the shape ccording to 3GPP TS 23.032) are used to encode the shape itself 
    -- in accordance with the encoding defined in 3GPP TS 23.032
    --
    -- An Add-GeographicalInformation parameter, whether valid or invalid, 
    -- received together with a valid Ext-GeographicalInformation parameter in 
    -- the same message shall be discarded.
    --
    -- An Add-GeographicalInformation parameter containing any shape not defined 
    -- in 3GPP TS 23.032 or an incorrect number of octets or coding according to 
    -- 3GPP TS 23.032 shall be treated as invalid data by a receiver if not 
    -- received together with a valid Ext-GeographicalInformation parameter in 
    -- the same message.

maxAdd-GeographicalInformation  INTEGER ::= 91
    -- the maximum length allows support for all the shapes currently defined in 
    -- 3GPP TS 23.032


SubscriberLocationReport-Arg ::= SEQUENCE {
    lcs-Event       LCS-Event,
    lcs-ClientID    LCS-ClientID, 
    lcsLocationInfo LCSLocationInfo,
    msisdn      [0] ISDN-AddressString  OPTIONAL,
    imsi            [1] IMSI        OPTIONAL,
    imei            [2] IMEI        OPTIONAL,
    na-ESRD     [3] ISDN-AddressString  OPTIONAL,
    na-ESRK     [4] ISDN-AddressString  OPTIONAL,
    locationEstimate    [5] Ext-GeographicalInformation OPTIONAL,
    ageOfLocationEstimate   [6] AgeOfLocationInformation    OPTIONAL,
    extensionContainer  [7] ExtensionContainer  OPTIONAL,
    ..., 
    add-LocationEstimate	[8] Add-GeographicalInformation	OPTIONAL,
    deferredmt-lrData	[9] Deferredmt-lrData	OPTIONAL, 
    lcs-ReferenceNumber	[10] LCS-ReferenceNumber	OPTIONAL,
    geranPositioningData	[11] PositioningDataInformation	OPTIONAL,
    utranPositioningData	[12] UtranPositioningDataInfo	OPTIONAL,
    cellIdOrSai	[13]	CellGlobalIdOrServiceAreaIdOrLAI	OPTIONAL,
    h-gmlc-Address	[14]	GSN-Address	OPTIONAL,
    lcsServiceTypeID	[15]	LCSServiceTypeID	OPTIONAL,
    sai-Present	[17] NULL		OPTIONAL,
    pseudonymIndicator	[18] NULL		OPTIONAL }

-- one of msisdn or imsi is mandatory
-- a location estimate that is valid for the locationEstimate parameter should 
-- be transferred in this parameter in preference to the add-LocationEstimate.
-- the deferredmt-lrData parameter shall be included if and only if the lcs-Event
-- indicates a deferredmt-lrResponse.
-- if the lcs-Event indicates a deferredmt-lrResponse then the locationEstimate 
-- and the add-locationEstimate parameters shall not be sent if the 
-- supportedGADShapes parameter had been received in ProvideSubscriberLocation-Arg
-- and the shape encoded in locationEstimate or add-LocationEstimate was not marked
-- as supported in supportedGADShapes. In such a case terminationCause 
-- in deferredmt-lrData shall be present with value 
-- shapeOfLocationEstimateNotSupported. 
-- If a lcs event indicates deferred mt-lr response, the lcs-Reference number shall be 
-- included. 
-- sai-Present indicates that the cellIdOrSai parameter contains a Service Area Identity.


Deferredmt-lrData ::= SEQUENCE {
    deferredLocationEventType	DeferredLocationEventType,
    terminationCause	[0] TerminationCause	OPTIONAL,
    lcsLocationInfo	[1] LCSLocationInfo	OPTIONAL,
    ...}
    -- lcsLocationInfo may be included only if a terminationCause is present 
    -- indicating mt-lrRestart.


LCS-Event ::= ENUMERATED {
    emergencyCallOrigination  (0),
    emergencyCallRelease  (1), 
    mo-lr  (2),
    ...,
    deferredmt-lrResponse  (3) }
    --  exception handling:
    --  a SubscriberLocationReport-Arg containing an unrecognized LCS-Event
    --  shall be rejected by a receiver with a return error cause of unexpected data value

TerminationCause ::= ENUMERATED {
    normal  (0),
    errorundefined  (1),
    internalTimeout  (2),
    congestion  (3),
    mt-lrRestart  (4),
    privacyViolation  (5),
    ...,
    shapeOfLocationEstimateNotSupported (6) } 
    -- mt-lrRestart shall be used to trigger the GMLC to restart the location 
    -- procedure, either because the sending node knows that the terminal has 
    -- moved under coverage of another MSC or SGSN (e.g. Send Identification 
    -- received), or because the subscriber has been deregistered due to a 
    -- Cancel Location received from HLR.
    --
    -- exception handling
    -- an unrecognized value shall be treated the same as value 1 
    -- (errorundefined)


SubscriberLocationReport-Res ::= SEQUENCE {
    extensionContainer  ExtensionContainer  OPTIONAL, 
    ...,
    na-ESRK		[0] ISDN-AddressString	OPTIONAL,
    na-ESRD		[1] ISDN-AddressString	OPTIONAL }

-- na-ESRK and na-ESRD are mutually exclusive
--
-- exception handling
-- receipt of both na-ESRK and na-ESRD shall be treated the same as a return error

--not used 
--not used END
--not used 
--not used  
--------------------------------------------------------------------------------
--------------------------------------------------------------------------------
--------------------------------------------------------------------------------
--[CL] 29002-562.doc 17.7.14 Secure transport data types

-- Module ----------------------------------------------------------------------
--------------------------------------------------------------------------------
-- MAP ST Data Types.
--------------------------------------------------------------------------------
--------------------------------------------------------------------------------

--not used  
--not used MAP-ST-DataTypes {
--not used    ccitt identified-organization (4) etsi (0) mobileDomain (0)
--not used    gsm-Network (1) modules (3) map-ST-DataTypes (27) version8 (8)}
--not used 
--not used DEFINITIONS
--not used IMPLICIT TAGS
--not used ::=
--not used BEGIN
--not used 
--not used EXPORTS
--not used     SecureTransportArg,
--not used     SecureTransportRes,
--not used     SecurityHeader,
--not used     ProtectedPayload
--not used ;
--not used 
--not used IMPORTS
--not used     IMSI,
--not used 
--not used FROM MAP-CommonDataTypes {
--not used    ccitt identified-organization (4) etsi (0) mobileDomain (0)
--not used    gsm-Network (1) modules (3) map-CommonDataTypes (18) version8 (8)}
--not used ;

SecureTransportArg ::= SEQUENCE {
    securityHeader      SecurityHeader,
    protectedPayload        ProtectedPayload    OPTIONAL
    }
    -- The protectedPayload carries the result of applying the security function 
    -- defined in 3G TS 33.200 to the encoding of the argument of the securely
    -- transported operation

SecureTransportRes ::= SEQUENCE {
    securityHeader      SecurityHeader,
    protectedPayload        ProtectedPayload    OPTIONAL
    }
    -- The protectedPayload carries the result of applying the security function 
    -- defined in 3G TS 33.200 to the encoding of the result of the securely
    -- transported operation

SecurityHeader ::= SEQUENCE {
    securityParametersIndex	SecurityParametersIndex,
    originalComponentIdentifier OriginalComponentIdentifier,
    initialisationVector     InitialisationVector    OPTIONAL,
    --initialisationVector    [4] InitialisationVector    OPTIONAL,
    ...}

ProtectedPayload ::= OCTET STRING(SIZE(1..3438))
    -- In protection mode 0 (noProtection) the ProtectedPayload carries the transfer
        -- syntax value of the component parameter identified by the
        -- originalComponentIdentifier.
    -- In protection mode 1 (integrityAuthenticity) the protectedPayload carries 
        -- parameter identified by the originalComponentIdentifier, followed by
        -- the 32 bit integrity check value.
        -- The integrity check value is the result of applying the hash algorithm
        -- to the concatenation of the transfer syntax value of the SecurityHeader,
        -- and the transfer syntax value of the component parameter. 
    -- In protection mode 2 (confidentialityIntegrityAuthenticity) the protected
        -- payload carries the encrypted transfer syntax
        -- value of the component parameter identified by the
        -- originalComponentIdentifier, followed by the 32 bit integrity check value.
        -- The integrity check value is the result of applying the hash algorithm
        -- to the concatenation of the transfer syntax value of the SecurityHeader,
        -- and the encrypted transfer syntax value of the component parameter. 
    -- See 33.200.
    -- The length of the protectedPayload is adjusted according to the capabilities of
    -- the lower protocol layers

    
SecurityParametersIndex ::= OCTET STRING (SIZE(4))

InitialisationVector ::= OCTET STRING (SIZE(14))
    -- the internal structure is defined as follows:
    -- Octets 1 to 4 : TVP. The TVP is a 32 bit time stamp. Its value is binary 
    --                 coded and indicates the number of intervals of 100 
    --                 milliseconds elapsed since 1st January 2002, 0:00:00 UTC
    -- Octets 5 to 10: NE-Id. The NE-Id uniquely identifies the sending network 
    --                 entity within the PLMN. It is the entity's E.164 number 
    --                 without CC and NDC. It is TBCD-coded, padded with zeros.
    -- Octets 11 to 14: PROP. This 32 bit value is used to make the
    --		      InitialisationVector unique within the same TVP period.
    --		      The content is not standardized.


OriginalComponentIdentifier ::= CHOICE {
    operationCode   [0] OperationCode,
    errorCode       [1] ErrorCode,
    userInfo        [2] NULL}

OperationCode ::= CHOICE {
    localValue  INTEGER,
    globalValue OBJECT IDENTIFIER}

ErrorCode ::= CHOICE {
    localValue  INTEGER,
    globalValue OBJECT IDENTIFIER}
--not used 
--not used END
--not used 
--------------------------------------------------------------------------------
--------------------------------------------------------------------------------
--------------------------------------------------------------------------------



--------------------------------------------------------------------------------
--------------------------------------------------------------------------------
-- Added global module definition (end).
--------------------------------------------------------------------------------
--------------------------------------------------------------------------------



END
