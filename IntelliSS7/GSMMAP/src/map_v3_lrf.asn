--------------------------------------------------------------------------------
--                                                                            --
--      Copyright 1999 IntelliNet Technologies, Inc. All Rights Reserved.     --
--              Manufactured in the United States of America.                 --
--        1990 W. New Haven Ste. 312, Melbourne, Florida, 32904 U.S.A.        --
--                                                                            --
--    This product and related documentation is protected by copyright and    --
--    distributed under licenses restricting its use, copying, distribution   --
--    and decompilation.  No part of this product or related documentation    --
--    may be reproduced in any form by any means without prior written        --
--    authorization of IntelliNet Technologies and its licensors, if any.     --
--                                                                            --
--    RESTRICTED RIGHTS LEGEND:  Use, duplication, or disclosure by the       --
--    government is subject to restrictions as set forth in subparagraph      --
--    (c)(1)(ii) of the Rights in Technical Data and Computer Software        --
--    clause at DFARS 252.227-7013 and FAR 52.227-19.                         --
--                                                                            --
--------------------------------------------------------------------------------
--                                                                            --
--  CONTRACT: INTERNAL                                                        --
--                                                                            --
--------------------------------------------------------------------------------
--
--  ID: $Id: map_v3_lrf.asn,v 9.1 2005/03/23 12:51:28 cvsadmin Exp $
--
--------------------------------------------------------------------------------

--------------------------------------------------------------------------------
--------------------------------------------------------------------------------
--
--  ASN.1 Module for GSM MAP Phase 2+ (MAP V3).
--
--  LRF (Local Reference Format) version (from specification).
--
--------------------------------------------------------------------------------
--------------------------------------------------------------------------------

--
--
--  Specification identification:
--
--
--	ETS 300 974
--	TELECOMMUNICATION April 2000
--	STANDARD Tenth Edition
--      Source: SMG Reference: RE/SMG-030902QR9
--
--	Digital cellular telecommunications system (Phase 2+);
--	Mobile Application Part (MAP) specification
--	(GSM 09.02 version 5.14.1 Release 1996)
--
--


--
--  Modules currently not generated (and therefore commented out with the 
--  comment prefix '-''-'"not impl "):
--
--  o   MAP-ApplicationContexts - contains only OBJECT IDENTIFIER values that
--      are hand-written, not generated.
--
--  o   MAP-Protocol - contains only INTEGER values that are hand-written, not
--      generated.
--
--  o   MAP-MobileServiceOperations - contains ASN.1 macros (OPERATION).
--
--  o   MAP-OperationAndMaintenanceOperations - contains ASN.1 macros 
--      (OPERATION).
--
--  o   MAP-CallHandlingOperations - contains ASN.1 macros (OPERATION).
--
--  o   MAP-SupplementaryServiceOperations - contains ASN.1 macros (OPERATION).
--  
--  o   MAP-ShortMessageServiceOperations - contains ASN.1 macros (OPERATION).
--
--  o   MAP-Errors - contains ASN.1 macros (ERROR).
-- 
-- 
--

--
--  An extra explicit tag (i.e. "[3]" has been removed in the following 
--  SEQUENCE type definition (probably typos in the specification):
--
--  o   SendRoutingInfoRes ::= SEQUENCE instead of ::= [3] SEQUENCE.
--
--
--  Only one module (named MAP-V3) is used. All information related to modules
--  import and export is commented out with the comment prefix '-''-'
--  "not used ".
--

--
--  Added phase2 bit to BIT STRING type SupportedCamelPhases. To be in sync with
--  MAP V4.
--
--  Modified type InterrogateSS-Res. To be in sync with MAP V4. Required to add
--  the type GenericServiceInfo from MAP V4.
--  
--	Modified type LocationInfoWithLMSI. To be in sync with MAP V4. Changed first
--  field name to "networkNode-Number". 
-- 
--  Added mnrg-Set bit to BIT STRING type MW-Status.
--
--  Modified type RegionalSubscriptionResponse. To be in sync with MAP v4
--  (instead of MAP V2). Changed first field name to 
--  "networkNode-AreaRestricted".
--


--------------------------------------------------------------------------------
--------------------------------------------------------------------------------
-- Added global module definition (begin).
--------------------------------------------------------------------------------
--------------------------------------------------------------------------------

MAP-V3

DEFINITIONS

IMPLICIT TAGS

::=

BEGIN

--------------------------------------------------------------------------------
--------------------------------------------------------------------------------

--------------------------------------------------------------------------------
--------------------------------------------------------------------------------


-- Module ----------------------------------------------------------------------
--------------------------------------------------------------------------------
-- MAP Application Contexts.
--------------------------------------------------------------------------------
--------------------------------------------------------------------------------

--not impl MAP-ApplicationContexts { 
--not impl ccitt identified-organization (4) etsi (0) mobileDomain (0)
--not impl gsm-Network (1) modules (3) map-ApplicationContexts (2) version3 (3)}
--not impl DEFINITIONS
--not impl ::=
--not impl BEGIN
-- EXPORTS everything
--not impl IMPORTS
--not impl gsm-NetworkId,
--not impl ac-Id
--not impl FROM MobileDomainDefinitions {
--not impl ccitt (0) identified-organization (4) etsi (0) mobileDomain (0)
--not impl mobileDomainDefinitions (0) version1 (1)}
--not impl ;
-- application-context-names
--not impl map-ac OBJECT IDENTIFIER ::= {gsm-NetworkId ac-Id}
--not impl networkLocUpContext-v3 OBJECT IDENTIFIER ::=
--not impl {map-ac networkLocUp(1) version3(3)}
--not impl locationCancellationContext-v2 OBJECT IDENTIFIER ::=
--not impl {map-ac locationCancel(2) version2(2)}
--not impl roamingNumberEnquiryContext-v3 OBJECT IDENTIFIER ::=
--not impl {map-ac roamingNbEnquiry(3) version3(3)}
--not impl locationInfoRetrievalContext-v3 OBJECT IDENTIFIER ::=
--not impl {map-ac locInfoRetrieval(5) version3(3)}
--not impl resetContext-v2 OBJECT IDENTIFIER ::=
--not impl {map-ac reset(10) version2(2)}
--not impl handoverControlContext-v2 OBJECT IDENTIFIER ::=
--not impl {map-ac handoverControl(11) version2(2)}
--not impl equipmentMngtContext-v2 OBJECT IDENTIFIER ::=
--not impl {map-ac equipmentMngt(13) version2(2)}
--not impl infoRetrievalContext-v2 OBJECT IDENTIFIER ::=
--not impl {map-ac infoRetrieval(14) version2(2)}
--not impl interVlrInfoRetrievalContext-v2 OBJECT IDENTIFIER ::=
--not impl {map-ac interVlrInfoRetrieval(15) version2(2)}
--not impl subscriberDataMngtContext-v3 OBJECT IDENTIFIER ::=
--not impl {map-ac subscriberDataMngt(16) version3(3)}
--not impl tracingContext-v3 OBJECT IDENTIFIER ::=
--not impl {map-ac tracing(17) version3(3)}
--not impl networkFunctionalSsContext-v2 OBJECT IDENTIFIER ::=
--not impl {map-ac networkFunctionalSs(18) version2(2)}
--not impl networkUnstructuredSsContext-v2 OBJECT IDENTIFIER ::=
--not impl {map-ac networkUnstructuredSs(19) version2(2)}
--not impl shortMsgGatewayContext-v3 OBJECT IDENTIFIER ::=
--not impl {map-ac shortMsgGateway(20) version3(3)}
--not impl shortMsgMO-RelayContext-v3 OBJECT IDENTIFIER ::=
--not impl {map-ac shortMsgMO-Relay(21) version3(3)}
--not impl 
--not impl shortMsgAlertContext-v2 OBJECT IDENTIFIER ::=
--not impl {map-ac shortMsgAlert(23) version2(2)}
--not impl mwdMngtContext-v2 OBJECT IDENTIFIER ::=
--not impl {map-ac mwdMngt(24) version2(2)}
--not impl shortMsgMT-RelayContext-v3 OBJECT IDENTIFIER ::=
--not impl {map-ac shortMsgMT-Relay(25) version3(3)}
--not impl imsiRetrievalContext-v2 OBJECT IDENTIFIER ::=
--not impl {map-ac imsiRetrieval(26) version2(2)}
--not impl msPurgingContext-v2 OBJECT IDENTIFIER ::=
--not impl {map-ac msPurging(27) version2(2)}
--not impl subscriberInfoEnquiryContext-v3 OBJECT IDENTIFIER ::=
--not impl {map-ac subscriberInfoEnquiry(28) version3(3)}
--not impl anyTimeInfoEnquiryContext-v3 OBJECT IDENTIFIER ::=
--not impl {map-ac anyTimeInfoEnquiry(29) version3(3)}
--not impl callControlTransferContext-v3 OBJECT IDENTIFIER ::=
--not impl {map-ac callControlTransfer(6) version3(3)}
-- The following Object Identifiers are reserved for application-
-- contexts existing in previous versions of the protocol
-- AC Name & Version Object Identifier
-- 
-- networkLocUpContext-v1 map-ac networkLocUp (1) version1 (1) 
-- networkLocUpContext-v2 map-ac networkLocUp (1) version2 (2) 
-- locationCancellationContext-v1 map-ac locationCancellation (2) version1 (1) 
-- roamingNumberEnquiryContext-v1 map-ac roamingNumberEnquiry (3) version1 (1) 
-- roamingNumberEnquiryContext-v2 map-ac roamingNumberEnquiry (3) version2 (2) 
-- locationInfoRetrievalContext-v1 map-ac locationInfoRetrieval (5) version1 (1) 
-- locationInfoRetrievalContext-v2 map-ac locationInfoRetrieval (5) version2 (2) 
-- resetContext-v1 map-ac reset (10) version1 (1) 
-- handoverControlContext-v1 map-ac handoverControl (11) version1 (1) 
-- equipmentMngtContext-v1 map-ac equipmentMngt (13) version1 (1) 
-- infoRetrievalContext-v1 map-ac infoRetrieval (14) version1 (1) 
-- subscriberDataMngtContext-v1 map-ac subscriberDataMngt (16) version1 (1) 
-- subscriberDataMngtContext-v2 map-ac subscriberDataMngt (16) version2 (2) 
-- tracingContext-v1 map-ac tracing (17) version1 (1) 
-- tracingContext-v2 map-ac tracing (17) version2 (2) 
-- networkFunctionalSsContext-v1 map-ac networkFunctionalSs (18) version1 (1) 
-- shortMsgGatewayContext-v1 map-ac shortMsgGateway (20) version1 (1) 
-- shortMsgGatewayContext-v2 map-ac shortMsgGateway (20) version2 (2) 
-- shortMsgRelayContext-v1 map-ac shortMsgRelay (21) version1 (1) 
-- shortMsgAlertContext-v1 map-ac shortMsgAlert (23) version1 (1) 
-- mwdMngtContext-v1 map-ac mwdMngt (24) version1 (1) 
-- shortMsgMT-RelayContext-v2 map-ac shortMsgMT-Relay (25) version2 (2) 

--not impl 
--not impl END 
--not impl 

--------------------------------------------------------------------------------
--------------------------------------------------------------------------------
--------------------------------------------------------------------------------


-- Module ----------------------------------------------------------------------
--------------------------------------------------------------------------------
-- MAP Dialogue Information.
--------------------------------------------------------------------------------
--------------------------------------------------------------------------------


--not used MAP-DialogueInformation { 
--not used ccitt identified-organization (4) etsi (0) mobileDomain (0) 
--not used gsm-Network (1) modules (3) map-DialogueInformation (3) version3 (3)} 
--not used 
--not used DEFINITIONS 
--not used 
--not used IMPLICIT TAGS 
--not used 
--not used ::= 
--not used 
--not used BEGIN 
--not used 
--not used EXPORTS 
--not used map-DialogueAS, 
--not used MAP-DialoguePDU 
--not used ; 
--not used 
--not used IMPORTS 
--not used gsm-NetworkId, 
--not used as-Id 
--not used FROM MobileDomainDefinitions { 
--not used ccitt (0) identified-organization (4) etsi (0) mobileDomain (0) 
--not used 
--not used mobileDomainDefinitions (0) version1 (1)} 
--not used 
--not used AddressString 
--not used FROM MAP-CommonDataTypes { 
--not used ccitt identified-organization (4) etsi (0) mobileDomain (0) 
--not used gsm-Network(1) modules (3) map-CommonDataTypes (18) version3 (3)} 
--not used 
--not used ExtensionContainer 
--not used FROM MAP-ExtensionDataTypes { 
--not used ccitt identified-organization (4) etsi (0) mobileDomain (0) 
--not used gsm-Network (1) modules (3) map-ExtensionDataTypes (21) version3 (3)} 
--not used 
--not used ; 
--not used 
--not used 
-- abstract syntax name for MAP-DialoguePDU 
--not used 
--not used map-DialogueAS OBJECT IDENTIFIER ::= 
--not used {gsm-NetworkId as-Id map-DialoguePDU (1) version1 (1)} 
--not used 

MAP-DialoguePDU ::= CHOICE { 
map-open [0] MAP-OpenInfo, 
map-accept [1] MAP-AcceptInfo, 
map-close [2] MAP-CloseInfo, 
map-refuse [3] MAP-RefuseInfo, 
map-userAbort [4] MAP-UserAbortInfo, 
map-providerAbort [5] MAP-ProviderAbortInfo} 

MAP-OpenInfo ::= SEQUENCE { 
destinationReference [0] AddressString OPTIONAL, 
originationReference [1] AddressString OPTIONAL, 
..., 
extensionContainer ExtensionContainer OPTIONAL 
-- extensionContainer must not be used in version 2 
} 

MAP-AcceptInfo ::= SEQUENCE { 
..., 
extensionContainer ExtensionContainer OPTIONAL 
-- extensionContainer must not be used in version 2 
} 

MAP-CloseInfo ::= SEQUENCE { 
..., 
extensionContainer ExtensionContainer OPTIONAL 
-- extensionContainer must not be used in version 2 
} 

MAP-RefuseInfo ::= SEQUENCE { 
reason Reason, 
..., 
extensionContainer ExtensionContainer OPTIONAL 
-- extensionContainer must not be used in version 2 
} 

Reason ::= ENUMERATED { 
noReasonGiven (0), 
invalidDestinationReference (1), 
invalidOriginatingReference (2)} 

MAP-UserAbortInfo ::= SEQUENCE { 
map-UserAbortChoice MAP-UserAbortChoice, 
..., 
extensionContainer ExtensionContainer OPTIONAL 
-- extensionContainer must not be used in version 2 
} 

MAP-UserAbortChoice ::= CHOICE { 
userSpecificReason [0] NULL, 
userResourceLimitation [1] NULL, 
resourceUnavailable [2] ResourceUnavailableReason, 
applicationProcedureCancellation [3] ProcedureCancellationReason} 

ResourceUnavailableReason ::= ENUMERATED { 
shortTermResourceLimitation (0), 
longTermResourceLimitation (1)} 

ProcedureCancellationReason ::= ENUMERATED { 
handoverCancellation (0), 
radioChannelRelease (1), 
networkPathRelease (2), 
callRelease (3), 
associatedProcedureFailure (4), 
tandemDialogueRelease (5), 
remoteOperationsFailure (6)} 

MAP-ProviderAbortInfo ::= SEQUENCE { 
map-ProviderAbortReason MAP-ProviderAbortReason, 
..., 
extensionContainer ExtensionContainer OPTIONAL 
-- extensionContainer must not be used in version 2 
} 

MAP-ProviderAbortReason ::= ENUMERATED { 
abnormalDialogue (0), 
invalidPDU (1)
} 

------------------------------------------------------------
-- Added type Map-UserInfo.
------------------------------------------------------------

MAP-UserInfo ::= SEQUENCE OF EXTERNAL
--not used 
--not used END 
--not used 

--------------------------------------------------------------------------------
--------------------------------------------------------------------------------
--------------------------------------------------------------------------------


-- Module ----------------------------------------------------------------------
--------------------------------------------------------------------------------
-- MAP Protocol.
--------------------------------------------------------------------------------
--------------------------------------------------------------------------------

--not impl MAP-Protocol { 
--not impl ccitt identified-organization (4) etsi (0) mobileDomain (0) 
--not impl gsm-Network (1) modules (3) map-Protocol (4) version3 (3)} 
--not impl 
--not impl DEFINITIONS 
--not impl 
--not impl ::= 
--not impl 
--not impl BEGIN 
--not impl 
--not impl IMPORTS 
--not impl UpdateLocation, 
--not impl CancelLocation, 
--not impl PurgeMS, 
--not impl SendIdentification, 
--not impl PrepareHandover, 
--not impl SendEndSignal, 
--not impl ProcessAccessSignalling, 
--not impl ForwardAccessSignalling, 
--not impl PrepareSubsequentHandover, 
--not impl SendAuthenticationInfo, 
--not impl CheckIMEI, 
--not impl InsertSubscriberData, 
--not impl DeleteSubscriberData, 
--not impl Reset, 
--not impl ForwardCheckSS-Indication, 
--not impl RestoreData, 
--not impl ProvideSubscriberInfo, 
--not impl AnyTimeInterrogation 
--not impl 
--not impl FROM MAP-MobileServiceOperations { 
--not impl ccitt identified-organization (4) etsi (0) mobileDomain (0) 
--not impl gsm-Network (1) modules (3) map-MobileServiceOperations (5) 
--not impl version3 (3)} 
--not impl 
--not impl ActivateTraceMode, 
--not impl DeactivateTraceMode, 
--not impl SendIMSI 
--not impl FROM MAP-OperationAndMaintenanceOperations { 
--not impl ccitt identified-organization (4) etsi (0) mobileDomain (0) 
--not impl gsm-Network (1) modules (3) map-OperationAndMaintenanceOperations (6) 
--not impl version3 (3)} 
--not impl 
--not impl SendRoutingInfo, 
--not impl ProvideRoamingNumber, 
--not impl ResumeCallHandling 
--not impl FROM MAP-CallHandlingOperations { 
--not impl ccitt identified-organization (4) etsi (0) mobileDomain (0) 
--not impl gsm-Network (1) modules (3) map-CallHandlingOperations (7) 
--not impl version3 (3)} 
--not impl 
--not impl RegisterSS, 
--not impl EraseSS, 
--not impl ActivateSS, 
--not impl DeactivateSS, 
--not impl InterrogateSS, 
--not impl ProcessUnstructuredSS-Request, 
--not impl UnstructuredSS-Request, 
--not impl UnstructuredSS-Notify, 
--not impl RegisterPassword, 
--not impl GetPassword 
--not impl FROM MAP-SupplementaryServiceOperations { 
--not impl ccitt identified-organization (4) etsi (0) mobileDomain (0) 
--not impl gsm-Network (1) modules (3) map-SupplementaryServiceOperations (8) 
--not impl version3 (3)} 
--not impl 
--not impl SendRoutingInfoForSM, 
--not impl MO-ForwardSM, 
--not impl MT-ForwardSM, 
--not impl ReportSM-DeliveryStatus, 
--not impl AlertServiceCentre, 
--not impl InformServiceCentre, 
--not impl ReadyForSM 
--not impl FROM MAP-ShortMessageServiceOperations { 
--not impl ccitt identified-organization (4) etsi (0) mobileDomain (0) 
--not impl gsm-Network (1) modules (3) map-ShortMessageServiceOperations (9) 
--not impl version3 (3)} 
--not impl 
--not impl SystemFailure, 
--not impl DataMissing, 
--not impl UnexpectedDataValue, 
--not impl FacilityNotSupported, 
--not impl UnknownSubscriber, 
--not impl NumberChanged, 
--not impl UnknownMSC, 
--not impl UnidentifiedSubscriber, 
--not impl UnknownEquipment, 
--not impl RoamingNotAllowed, 
--not impl IllegalSubscriber, 
--not impl IllegalEquipment, 
--not impl BearerServiceNotProvisioned, 
--not impl TeleserviceNotProvisioned, 
--not impl NoHandoverNumberAvailable, 
--not impl SubsequentHandoverFailure, 
--not impl TracingBufferFull, 
--not impl OR-NotAllowed, 
--not impl NoRoamingNumberAvailable, 
--not impl AbsentSubscriber, 
--not impl BusySubscriber, 
--not impl NoSubscriberReply, 
--not impl CallBarred, 
--not impl ForwardingViolation, 
--not impl ForwardingFailed, 
--not impl CUG-Reject, 
--not impl ATI-NotAllowed, 
--not impl IllegalSS-Operation, 
--not impl SS-ErrorStatus, 
--not impl SS-NotAvailable, 
--not impl SS-SubscriptionViolation, 
--not impl SS-Incompatibility, 
--not impl UnknownAlphabet, 
--not impl USSD-Busy, 
--not impl PW-RegistrationFailure, 
--not impl NegativePW-Check, 
--not impl NumberOfPW-AttemptsViolation, 
--not impl SubscriberBusyForMT-SMS, 
--not impl SM-DeliveryFailure, 
--not impl MessageWaitingListFull, 
--not impl AbsentSubscriberSM 
--not impl FROM MAP-Errors { 
--not impl ccitt identified-organization (4) etsi (0) mobileDomain (0) 
--not impl gsm-Network (1) modules (3) map-Errors (10) version3 (3)} 
--not impl ; 
--not impl 
--not impl 
-- location registration operation codes 
--not impl 
--not impl updateLocation UpdateLocation ::= localValue 2 
--not impl cancelLocation CancelLocation ::= localValue 3 
--not impl purgeMS PurgeMS ::= localValue 67 
--not impl sendIdentification SendIdentification ::= localValue 55 
--not impl 
--not impl 
-- handover operation codes 
--not impl 
--not impl prepareHandover PrepareHandover ::= localValue 68 
--not impl sendEndSignal SendEndSignal ::= localValue 29 
--not impl processAccessSignalling ProcessAccessSignalling ::= localValue 33 
--not impl forwardAccessSignalling ForwardAccessSignalling ::= localValue 34 
--not impl prepareSubsequentHandover PrepareSubsequentHandover ::= 
--not impl localValue 69 
--not impl 
--not impl 
-- authentication operation codes 
--not impl 
--not impl sendAuthenticationInfo SendAuthenticationInfo ::= localValue 56 
--not impl 
--not impl 
-- IMEI MANAGEMENT operation codes 
--not impl 
--not impl checkIMEI CheckIMEI ::= localValue 43 
--not impl 
--not impl 
-- subscriber management operation codes 
--not impl 
--not impl insertSubscriberData InsertSubscriberData ::= localValue 7 
--not impl deleteSubscriberData DeleteSubscriberData ::= localValue 8 
--not impl 
--not impl 
-- fault recovery operation codes 
--not impl 
--not impl reset Reset ::= localValue 37 
--not impl forwardCheckSS-Indication ForwardCheckSS-Indication ::= 
--not impl localValue 38 
--not impl restoreData RestoreData ::= localValue 57 
--not impl 
--not impl 
-- operation and maintenance operation codes 
--not impl 
--not impl activateTraceMode ActivateTraceMode ::= localValue 50 
--not impl deactivateTraceMode DeactivateTraceMode ::= localValue 51 
--not impl sendIMSI SendIMSI ::= localValue 58 
--not impl 
--not impl 
-- call handling operation codes 
--not impl 
--not impl sendRoutingInfo SendRoutingInfo ::= localValue 22 
--not impl provideRoamingNumber ProvideRoamingNumber ::= localValue 4 
--not impl resumeCallHandling ResumeCallHandling ::= localValue 6 
--not impl 
--not impl 
-- supplementary service handling operation codes 
--not impl 
--not impl registerSS RegisterSS ::= localValue 10 
--not impl eraseSS EraseSS ::= localValue 11 
--not impl activateSS ActivateSS ::= localValue 12 
--not impl deactivateSS DeactivateSS ::= localValue 13 
--not impl interrogateSS InterrogateSS ::= localValue 14 
--not impl processUnstructuredSS-Request ProcessUnstructuredSS-Request ::= 
--not impl localValue 59 
--not impl unstructuredSS-Request UnstructuredSS-Request ::= localValue 60 
--not impl unstructuredSS-Notify UnstructuredSS-Notify ::= localValue 61 
--not impl registerPassword RegisterPassword ::= localValue 17 
--not impl getPassword GetPassword ::= localValue 18 
--not impl 
--not impl 
-- short message service operation codes 
--not impl 
--not impl sendRoutingInfoForSM SendRoutingInfoForSM ::= localValue 45 
--not impl mo-forwardSM MO-ForwardSM ::= localValue 46 
--not impl mt-forwardSM MT-ForwardSM ::= localValue 44 
--not impl reportSM-DeliveryStatus ReportSM-DeliveryStatus ::= localValue 47 
--not impl informServiceCentre InformServiceCentre ::= localValue 63 
--not impl alertServiceCentre AlertServiceCentre ::= localValue 64 
--not impl readyForSM ReadyForSM ::= localValue 66 
--not impl 
-- provide subscriber info operation codes 
--not impl 
--not impl provideSubscriberInfo ProvideSubscriberInfo ::= localValue 70 
--not impl 
-- any time interrogation operation codes 
--not impl 
--not impl anyTimeInterrogation AnyTimeInterrogation ::= localValue 71 
--not impl 
-- generic error codes 
--not impl 
--not impl systemFailure SystemFailure ::= localValue 34 
--not impl dataMissing DataMissing ::= localValue 35 
--not impl unexpectedDataValue UnexpectedDataValue ::= localValue 36 
--not impl facilityNotSupported FacilityNotSupported ::= localValue 21 
--not impl 
--not impl 
-- identification and numbering error codes 
--not impl 
--not impl unknownSubscriber UnknownSubscriber ::= localValue 1 
--not impl numberChanged NumberChanged ::= localValue 44 
--not impl unknownMSC UnknownMSC ::= localValue 3 
--not impl unidentifiedSubscriber UnidentifiedSubscriber ::= localValue 5 
--not impl unknownEquipment UnknownEquipment ::= localValue 7 
--not impl 
--not impl 
-- subscription error codes 
--not impl 
--not impl roamingNotAllowed RoamingNotAllowed ::= localValue 8 
--not impl illegalSubscriber IllegalSubscriber ::= localValue 9 
--not impl illegalEquipment IllegalEquipment ::= localValue 12 
--not impl bearerServiceNotProvisioned BearerServiceNotProvisioned ::= 
--not impl localValue 10 
--not impl teleserviceNotProvisioned TeleserviceNotProvisioned ::= 
--not impl localValue 11 
--not impl 
--not impl 
-- handover error codes 
--not impl 
--not impl noHandoverNumberAvailable NoHandoverNumberAvailable ::= 
--not impl localValue 25 
--not impl subsequentHandoverFailure SubsequentHandoverFailure ::= 
--not impl localValue 26 
--not impl 
--not impl 
-- operation and maintenance error codes 
--not impl 
--not impl tracingBufferFull TracingBufferFull ::= localValue 40 
--not impl 
--not impl 
-- call handling error codes 
--not impl 
--not impl noRoamingNumberAvailable NoRoamingNumberAvailable ::= localValue 39 
--not impl absentSubscriber AbsentSubscriber ::= localValue 27 
--not impl busySubscriber BusySubscriber ::= localValue 45 
--not impl noSubscriberReply NoSubscriberReply ::= localValue 46 
--not impl callBarred CallBarred ::= localValue 13 
--not impl forwardingFailed ForwardingFailed ::= localValue 47 
--not impl or-NotAllowed OR-NotAllowed ::= localValue 48 
--not impl forwardingViolation ForwardingViolation ::= localValue 14 
--not impl cug-Reject CUG-Reject ::= localValue 15 
--not impl 
--not impl 
-- any time interrogation error codes 
--not impl ati-NotAllowed ATI-NotAllowed ::= localValue 49 
--not impl 
--not impl 
-- supplementary service error codes 
--not impl 
--not impl illegalSS-Operation IllegalSS-Operation ::= localValue 16 
--not impl ss-ErrorStatus SS-ErrorStatus ::= localValue 17 
--not impl ss-NotAvailable SS-NotAvailable ::= localValue 18 
--not impl ss-SubscriptionViolation SS-SubscriptionViolation ::= localValue 19 
--not impl ss-Incompatibility SS-Incompatibility ::= localValue 20 
--not impl unknownAlphabet UnknownAlphabet ::= localValue 71 
--not impl ussd-Busy USSD-Busy ::= localValue 72 
--not impl pw-RegistrationFailure PW-RegistrationFailure ::= localValue 37 
--not impl negativePW-Check NegativePW-Check ::= localValue 38 
--not impl numberOfPW-AttemptsViolation NumberOfPW-AttemptsViolation ::= 
--not impl localValue 43 
--not impl 
--not impl 
-- short message service error codes 
--not impl 
--not impl subscriberBusyForMT-SMS SubscriberBusyForMT-SMS ::= localValue 31 
--not impl sm-DeliveryFailure SM-DeliveryFailure ::= localValue 32 
--not impl messageWaitingListFull MessageWaitingListFull ::= localValue 33 
--not impl absentsubscriberSM AbsentSubscriberSM ::= localValue 6 
--not impl 
--not impl 
-- The following operation codes are reserved for operations 
-- existing in previous versions of the protocol 
--not impl 
-- Operation Name AC used Oper. Code 
-- 
-- sendParameters map-ac infoRetrieval (14) version1 (1) localValue 9 
-- processUnstructuredSS-Data map-ac networkFunctionalSs (18) version1 (1) localValue 19 
-- performHandover map-ac handoverControl (11) version1 (1) localValue 28 
-- performSubsequentHandover map-ac handoverControl (11) version1 (1) localValue 30 
-- noteInternalHandover map-ac handoverControl (11) version1 (1) localValue 35 
-- noteSubscriberPresent map-ac mwdMngt (24) version1 (1) localValue 48 
-- alertServiceCentreWithoutResult map-ac shortMsgAlert (23) version1 (1) localValue 49 
-- traceSubscriberActivity map-ac handoverControl (11) version1 (1) localValue 52 
-- beginSubscriberActivity map-ac networkFunctionalSs (18) version1 (1) localValue 54 

-- The following error codes are reserved for errors 
-- existing in previous versions of the protocol 

-- Error Name AC used Error Code 
-- 
-- unknownBaseStation map-ac handoverControl (11) version1 (1) localValue 2 
-- invalidTargetBaseStation map-ac handoverControl (11) version1 (1) localValue 23 
-- noRadioResourceAvailable map-ac handoverControl (11) version1 (1) localValue 24 

--not impl 
--not impl END 
--not impl 

--------------------------------------------------------------------------------
--------------------------------------------------------------------------------
--------------------------------------------------------------------------------


-- Module ----------------------------------------------------------------------
--------------------------------------------------------------------------------
-- MAP Mobile Service Operations.
--------------------------------------------------------------------------------
--------------------------------------------------------------------------------

--not impl MAP-MobileServiceOperations { 
--not impl ccitt identified-organization (4) etsi (0) mobileDomain (0) 
--not impl gsm-Network (1) modules (3) map-MobileServiceOperations (5) 
--not impl version3 (3)} 
--not impl 
--not impl DEFINITIONS 
--not impl 
--not impl ::= 
--not impl 
--not impl BEGIN 
--not impl 
--not impl EXPORTS 
--not impl 
-- location registration operations 
--not impl UpdateLocation, 
--not impl CancelLocation, 
--not impl PurgeMS, 
--not impl SendIdentification, 
--not impl 
-- subscriber information enquiry operations 
--not impl ProvideSubscriberInfo, 
--not impl 
-- any time information enquiry operations 
--not impl AnyTimeInterrogation, 
--not impl 
-- handover operations 
--not impl PrepareHandover, 
--not impl SendEndSignal, 
--not impl ProcessAccessSignalling, 
--not impl ForwardAccessSignalling, 
--not impl PrepareSubsequentHandover, 
--not impl 
-- authentication management operations 
--not impl SendAuthenticationInfo, 
--not impl 
-- IMEI management operations 
--not impl CheckIMEI, 
--not impl 
-- subscriber management operations 
--not impl InsertSubscriberData, 
--not impl DeleteSubscriberData, 
--not impl 
-- fault recovery operations 
--not impl Reset, 
--not impl ForwardCheckSS-Indication, 
--not impl RestoreData 
--not impl ; 
--not impl 
--not impl IMPORTS 
--not impl OPERATION 
--not impl FROM TCAPMessages { 
--not impl ccitt recommendation q 773 modules (2) messages (1) version2 (2)} 
--not impl 
--not impl SystemFailure, 
--not impl DataMissing, 
--not impl UnexpectedDataValue, 
--not impl UnknownSubscriber, 
--not impl UnknownMSC, 
--not impl UnidentifiedSubscriber, 
--not impl UnknownEquipment, 
--not impl RoamingNotAllowed, 
--not impl ATI-NotAllowed, 
--not impl NoHandoverNumberAvailable, 
--not impl SubsequentHandoverFailure 
--not impl FROM MAP-Errors { 
--not impl ccitt identified-organization (4) etsi (0) mobileDomain (0) 
--not impl gsm-Network (1) modules (3) map-Errors (10) version3 (3)} 
--not impl 
--not impl UpdateLocationArg, 
--not impl UpdateLocationRes, 
--not impl CancelLocationArg, 
--not impl PurgeMS-Arg, 
--not impl SendIdentificationRes, 
--not impl PrepareHO-Arg, 
--not impl PrepareHO-Res, 
--not impl PrepareSubsequentHO-Arg, 
--not impl SendAuthenticationInfoArg, 
--not impl SendAuthenticationInfoRes, 
--not impl EquipmentStatus, 
--not impl InsertSubscriberDataArg, 
--not impl InsertSubscriberDataRes, 
--not impl DeleteSubscriberDataArg, 
--not impl DeleteSubscriberDataRes, 
--not impl ResetArg, 
--not impl RestoreDataArg, 
--not impl RestoreDataRes, 
--not impl ProvideSubscriberInfoArg, 
--not impl ProvideSubscriberInfoRes, 
--not impl AnyTimeInterrogationArg, 
--not impl AnyTimeInterrogationRes 
--not impl 
--not impl FROM MAP-MS-DataTypes { 
--not impl ccitt identified-organization (4) etsi (0) mobileDomain (0) 
--not impl gsm-Network (1) modules (3) map-MS-DataTypes (11) version3 (3)} 
--not impl 
--not impl ExternalSignalInfo, 
--not impl TMSI, 
--not impl IMEI 
--not impl FROM MAP-CommonDataTypes { 
--not impl ccitt identified-organization (4) etsi (0) mobileDomain (0) 
--not impl gsm-Network (1) modules (3) map-CommonDataTypes (18) version3 (3)} 
--not impl ; 
--not impl 
--not impl 
-- location registration operations 
--not impl 
--not impl UpdateLocation ::= OPERATION 
--Timer m 
--not impl ARGUMENT 
--not impl updateLocationArg UpdateLocationArg 
--not impl RESULT 
--not impl updateLocationRes UpdateLocationRes 
--not impl ERRORS { 
--not impl SystemFailure, 
--not impl DataMissing, 
--not impl UnexpectedDataValue, 
--not impl UnknownSubscriber, 
--not impl RoamingNotAllowed} 
--not impl 
--not impl CancelLocation ::= OPERATION 
--Timer m 
--not impl ARGUMENT 
--not impl cancelLocationArg CancelLocationArg 
--not impl RESULT 
--not impl ERRORS { 
--not impl DataMissing, 
--not impl UnexpectedDataValue} 
--not impl 
--not impl PurgeMS ::= OPERATION 
--Timer m 
--not impl ARGUMENT 
--not impl purgeMS-Arg PurgeMS-Arg 
--not impl RESULT 
--not impl 
--not impl SendIdentification::= OPERATION 
--Timer s 
--not impl ARGUMENT 
--not impl tmsi TMSI 
--not impl RESULT 
--not impl sendIdentificationRes SendIdentificationRes 
--not impl ERRORS { 
--not impl DataMissing, 
--not impl UnidentifiedSubscriber} 
--not impl 
-- subscriber information enquiry operations 
--not impl 
--not impl ProvideSubscriberInfo ::= OPERATION 
--Timer m 
--not impl ARGUMENT 
--not impl provideSubscriberInfoArg ProvideSubscriberInfoArg 
--not impl RESULT 
--not impl provideSubscriberInfoRes ProvideSubscriberInfoRes 
--not impl ERRORS { 
--not impl DataMissing, 
--not impl UnexpectedDataValue} 
--not impl 
-- any time information enquiry operations 
--not impl 
--not impl AnyTimeInterrogation ::= OPERATION 
--Timer m 
--not impl ARGUMENT 
--not impl anyTimeInterrogationArg AnyTimeInterrogationArg 
--not impl RESULT 
--not impl anyTimeInterrogationRes AnyTimeInterrogationRes 
--not impl ERRORS { 
--not impl SystemFailure, 
--not impl ATI-NotAllowed, 
--not impl DataMissing, 
--not impl UnexpectedDataValue, 
--not impl UnknownSubscriber} 
-- handover operations 
--not impl 
--not impl PrepareHandover ::= OPERATION 
--Timer m 
--not impl ARGUMENT 
--not impl prepareHO-Arg PrepareHO-Arg 
--not impl RESULT 
--not impl prepareHO-Res PrepareHO-Res 
--not impl ERRORS { 
--not impl SystemFailure, 
--not impl DataMissing, 
--not impl UnexpectedDataValue, 
--not impl NoHandoverNumberAvailable} 
--not impl 
--not impl SendEndSignal ::= OPERATION 
--Timer l 
--not impl ARGUMENT 
--not impl bss-APDU ExternalSignalInfo 
--not impl RESULT 
--not impl 
--not impl ProcessAccessSignalling ::= OPERATION 
--Timer s 
--not impl ARGUMENT 
--not impl bss-APDU ExternalSignalInfo 
--not impl 
--not impl ForwardAccessSignalling ::= OPERATION 
--Timer s 
--not impl ARGUMENT 
--not impl bss-APDU ExternalSignalInfo 
--not impl 
--not impl PrepareSubsequentHandover ::= OPERATION 
--Timer m 
--not impl ARGUMENT 
--not impl prepareSubsequentHO-Arg PrepareSubsequentHO-Arg 
--not impl RESULT 
--not impl bss-APDU ExternalSignalInfo 
--not impl ERRORS { 
--not impl UnexpectedDataValue, 
--not impl DataMissing, 
--not impl UnknownMSC, 
--not impl SubsequentHandoverFailure} 
--not impl 
-- authentication management operations 
--not impl 
--not impl SendAuthenticationInfo ::= OPERATION 
--Timer m 
--not impl ARGUMENT 
--not impl sendAuthenticationInfoArg SendAuthenticationInfoArg 
--not impl RESULT 
--not impl sendAuthenticationInfoRes SendAuthenticationInfoRes 
-- optional 
--not impl ERRORS { 
--not impl SystemFailure, 
--not impl DataMissing, 
--not impl UnexpectedDataValue, 
--not impl UnknownSubscriber} 
--not impl 
-- IMEI management operations 
--not impl 
--not impl CheckIMEI ::= OPERATION 
--Timer m 
--not impl ARGUMENT 
--not impl imei IMEI 
--not impl RESULT 
--not impl equipmentStatus EquipmentStatus 
--not impl ERRORS { 
--not impl SystemFailure, 
--not impl DataMissing, 
--not impl UnknownEquipment} 
--not impl 
-- subscriber management operations 
--not impl 
--not impl InsertSubscriberData ::= OPERATION 
--Timer m 
--not impl ARGUMENT 
--not impl insertSubscriberDataArg InsertSubscriberDataArg 
--not impl RESULT 
--not impl insertSubscriberDataRes InsertSubscriberDataRes 
-- optional 
--not impl ERRORS { 
--not impl DataMissing, 
--not impl UnexpectedDataValue, 
--not impl UnidentifiedSubscriber} 
--not impl 
--not impl DeleteSubscriberData ::= OPERATION 
--Timer m 
--not impl ARGUMENT 
--not impl deleteSubscriberDataArg DeleteSubscriberDataArg 
--not impl RESULT 
--not impl deleteSubscriberDataRes DeleteSubscriberDataRes 
-- optional 
--not impl ERRORS { 
--not impl DataMissing, 
--not impl UnexpectedDataValue, 
--not impl UnidentifiedSubscriber} 
--not impl 
-- fault recovery operations 
--not impl 
--not impl Reset ::= OPERATION 
--Timer m 
--not impl ARGUMENT 
--not impl resetArg ResetArg 
--not impl 
--not impl ForwardCheckSS-Indication ::= OPERATION 
--Timer s 
--not impl 
--not impl RestoreData ::= OPERATION 
--Timer m 
--not impl ARGUMENT 
--not impl restoreDataArg RestoreDataArg 
--not impl RESULT 
--not impl restoreDataRes RestoreDataRes 
--not impl ERRORS { 
--not impl SystemFailure, 
--not impl DataMissing, 
--not impl UnexpectedDataValue, 
--not impl UnknownSubscriber} 
--not impl 
--not impl END 
--not impl 

--------------------------------------------------------------------------------
--------------------------------------------------------------------------------
--------------------------------------------------------------------------------


-- Module ----------------------------------------------------------------------
--------------------------------------------------------------------------------
-- MAP Operation And Maintenance Operations.
--------------------------------------------------------------------------------
--------------------------------------------------------------------------------

--not impl MAP-OperationAndMaintenanceOperations { 
--not impl ccitt identified-organization (4) etsi (0) mobileDomain (0) 
--not impl gsm-Network (1) modules (3) map-OperationAndMaintenanceOperations (6) 
--not impl version3 (3)} 
--not impl 
--not impl DEFINITIONS 
--not impl 
--not impl ::= 
--not impl 
--not impl BEGIN 
--not impl 
--not impl EXPORTS 
--not impl ActivateTraceMode, 
--not impl DeactivateTraceMode, 
--not impl SendIMSI 
--not impl ; 
--not impl 
--not impl IMPORTS 
--not impl OPERATION 
--not impl FROM TCAPMessages { 
--not impl ccitt recommendation q 773 modules (2) messages (1) version2 (2)} 
--not impl 
--not impl SystemFailure, 
--not impl DataMissing, 
--not impl UnexpectedDataValue, 
--not impl FacilityNotSupported, 
--not impl UnknownSubscriber, 
--not impl UnidentifiedSubscriber, 
--not impl TracingBufferFull 
--not impl FROM MAP-Errors { 
--not impl ccitt identified-organization (4) etsi (0) mobileDomain (0) 
--not impl gsm-Network (1) modules (3) map-Errors (10) version3 (3)} 
--not impl 
--not impl ActivateTraceModeArg, 
--not impl ActivateTraceModeRes, 
--not impl DeactivateTraceModeArg, 
--not impl DeactivateTraceModeRes 
--not impl FROM MAP-OM-DataTypes { 
--not impl ccitt identified-organization (4) etsi (0) mobileDomain (0) 
--not impl gsm-Network (1) modules (3) map-OM-DataTypes (12) version3 (3)} 
--not impl 
--not impl ISDN-AddressString, 
--not impl IMSI 
--not impl FROM MAP-CommonDataTypes { 
--not impl ccitt identified-organization (4) etsi (0) mobileDomain (0) 
--not impl gsm-Network (1) modules (3) map-CommonDataTypes (18) version3 (3)} 
--not impl ; 
--not impl 
--not impl 
--not impl ActivateTraceMode ::= OPERATION 
--Timer m 
--not impl ARGUMENT 
--not impl activateTraceModeArg ActivateTraceModeArg 
--not impl RESULT 
--not impl activateTraceModeRes ActivateTraceModeRes 
-- optional 
--not impl ERRORS { 
--not impl SystemFailure, 
--not impl DataMissing, 
--not impl UnexpectedDataValue, 
--not impl FacilityNotSupported, 
--not impl UnidentifiedSubscriber, 
--not impl TracingBufferFull} 
--not impl 
--not impl DeactivateTraceMode ::= OPERATION 
--Timer m 
--not impl ARGUMENT 
--not impl deactivateTraceModeArg DeactivateTraceModeArg 
--not impl RESULT 
--not impl deactivateTraceModeRes DeactivateTraceModeRes 
-- optional 
--not impl ERRORS { 
--not impl SystemFailure, 
--not impl DataMissing, 
--not impl UnexpectedDataValue, 
--not impl FacilityNotSupported, 
--not impl UnidentifiedSubscriber} 
--not impl 
--not impl SendIMSI ::= OPERATION 
--Timer m 
--not impl ARGUMENT 
--not impl msisdn ISDN-AddressString 
--not impl RESULT 
--not impl imsi IMSI 
--not impl ERRORS { 
--not impl DataMissing, 
--not impl UnexpectedDataValue, 
--not impl UnknownSubscriber} 
--not impl 
--not impl END 
--not impl 

--------------------------------------------------------------------------------
--------------------------------------------------------------------------------
--------------------------------------------------------------------------------


-- Module ----------------------------------------------------------------------
--------------------------------------------------------------------------------
-- MAP Call Handling Operations.
--------------------------------------------------------------------------------
--------------------------------------------------------------------------------


--not impl MAP-CallHandlingOperations { 
--not impl ccitt identified-organization (4) etsi (0) mobileDomain (0) 
--not impl gsm-Network (1) modules (3) map-CallHandlingOperations (7) 
--not impl version3 (3)} 
--not impl 
--not impl DEFINITIONS 
--not impl 
--not impl ::= 
--not impl 
--not impl BEGIN 
--not impl 
--not impl EXPORTS 
--not impl SendRoutingInfo, 
--not impl ProvideRoamingNumber, 
--not impl ResumeCallHandling 
--not impl ; 
--not impl 
--not impl IMPORTS 
--not impl OPERATION 
--not impl FROM TCAPMessages { 
--not impl ccitt recommendation q 773 modules (2) messages (1) version2 (2)} 
--not impl 
--not impl SystemFailure, 
--not impl DataMissing, 
--not impl UnexpectedDataValue, 
--not impl FacilityNotSupported, 
--not impl OR-NotAllowed, 
--not impl UnknownSubscriber, 
--not impl NumberChanged, 
--not impl BearerServiceNotProvisioned, 
--not impl TeleserviceNotProvisioned, 
--not impl NoRoamingNumberAvailable, 
--not impl AbsentSubscriber, 
--not impl BusySubscriber, 
--not impl NoSubscriberReply, 
--not impl CallBarred, 
--not impl ForwardingViolation, 
--not impl ForwardingFailed, 
--not impl CUG-Reject 
--not impl FROM MAP-Errors { 
--not impl ccitt identified-organization (4) etsi (0) mobileDomain (0) 
--not impl gsm-Network (1) modules (3) map-Errors (10) version3 (3)} 
--not impl SendRoutingInfoArg, 
--not impl SendRoutingInfoRes, 
--not impl ProvideRoamingNumberArg, 
--not impl ProvideRoamingNumberRes, 
--not impl ResumeCallHandlingArg, 
--not impl ResumeCallHandlingRes 
--not impl FROM MAP-CH-DataTypes { 
--not impl ccitt identified-organization (4) etsi (0) mobileDomain (0) 
--not impl gsm-Network (1) modules (3) map-CH-DataTypes (13) version3 (3)} 
--not impl 
--not impl ; 
--not impl 
--not impl SendRoutingInfo ::= OPERATION 
--Timer m 
--not impl ARGUMENT 
--not impl sendRoutingInfoArg SendRoutingInfoArg 
--not impl RESULT 
--not impl sendRoutingInfoRes SendRoutingInfoRes 
--not impl ERRORS { 
--not impl SystemFailure, 
--not impl DataMissing, 
--not impl UnexpectedDataValue, 
--not impl FacilityNotSupported, 
--not impl OR-NotAllowed, 
--not impl UnknownSubscriber, 
--not impl NumberChanged, 
--not impl BearerServiceNotProvisioned, 
--not impl TeleserviceNotProvisioned, 
--not impl AbsentSubscriber, 
--not impl BusySubscriber, 
--not impl NoSubscriberReply, 
--not impl CallBarred, 
--not impl CUG-Reject, 
--not impl ForwardingViolation} 
--not impl 
--not impl ProvideRoamingNumber ::= OPERATION 
--Timer m 
--not impl ARGUMENT 
--not impl provideRoamingNumberArg ProvideRoamingNumberArg 
--not impl RESULT 
--not impl provideRoamingNumberRes ProvideRoamingNumberRes 
--not impl ERRORS { 
--not impl SystemFailure, 
--not impl DataMissing, 
--not impl UnexpectedDataValue, 
--not impl FacilityNotSupported, 
--not impl OR-NotAllowed, 
--not impl AbsentSubscriber, 
--not impl NoRoamingNumberAvailable} 
--not impl 
--not impl ResumeCallHandling ::= OPERATION 
--Timer m 
--not impl ARGUMENT 
--not impl resumeCallHandlingArg ResumeCallHandlingArg 
--not impl RESULT 
--not impl resumeCallHandlingRes ResumeCallHandlingRes 
--not impl ERRORS { 
--not impl ForwardingFailed, 
--not impl OR-NotAllowed, 
--not impl UnexpectedDataValue} 
--not impl 
--not impl END 
--not impl 

--------------------------------------------------------------------------------
--------------------------------------------------------------------------------
--------------------------------------------------------------------------------


-- Module ----------------------------------------------------------------------
--------------------------------------------------------------------------------
-- MAP Supplementary Service Operations.
--------------------------------------------------------------------------------
--------------------------------------------------------------------------------

--not impl MAP-SupplementaryServiceOperations { 
--not impl ccitt identified-organization (4) etsi (0) mobileDomain (0) 
--not impl gsm-Network (1) modules (3) map-SupplementaryServiceOperations (8) 
--not impl version3 (3)} 
--not impl 
--not impl DEFINITIONS 
--not impl 
--not impl ::= 
--not impl 
--not impl BEGIN 
--not impl 
--not impl EXPORTS 
--not impl RegisterSS, 
--not impl EraseSS, 
--not impl ActivateSS, 
--not impl DeactivateSS, 
--not impl InterrogateSS, 
--not impl ProcessUnstructuredSS-Request, 
--not impl UnstructuredSS-Request, 
--not impl UnstructuredSS-Notify, 
--not impl RegisterPassword, 
--not impl GetPassword 
--not impl ; 
--not impl 
--not impl IMPORTS 
--not impl OPERATION 
--not impl FROM TCAPMessages { 
--not impl ccitt recommendation q 773 modules (2) messages (1) version2 (2)} 
--not impl 
--not impl SystemFailure, 
--not impl DataMissing, 
--not impl UnexpectedDataValue, 
--not impl BearerServiceNotProvisioned, 
--not impl TeleserviceNotProvisioned, 
--not impl CallBarred, 
--not impl IllegalSS-Operation, 
--not impl SS-ErrorStatus, 
--not impl SS-NotAvailable, 
--not impl SS-SubscriptionViolation, 
--not impl SS-Incompatibility, 
--not impl PW-RegistrationFailure, 
--not impl NegativePW-Check, 
--not impl NumberOfPW-AttemptsViolation, 
--not impl UnknownAlphabet, 
--not impl USSD-Busy, 
--not impl AbsentSubscriber, 
--not impl IllegalSubscriber, 
--not impl IllegalEquipment 
--not impl FROM MAP-Errors { 
--not impl ccitt identified-organization (4) etsi (0) mobileDomain (0) 
--not impl gsm-Network (1) modules (3) map-Errors (10) version3 (3)} 
--not impl 
--not impl RegisterSS-Arg, 
--not impl SS-Info, 
--not impl SS-ForBS-Code, 
--not impl InterrogateSS-Res, 
--not impl USSD-Arg, 
--not impl USSD-Res, 
--not impl Password, 
--not impl GuidanceInfo 
--not impl FROM MAP-SS-DataTypes { 
--not impl ccitt identified-organization (4) etsi (0) mobileDomain (0) 
--not impl gsm-Network (1) modules (3) map-SS-DataTypes (14) version3 (3)} 
--not impl 
--not impl SS-Code 
--not impl FROM MAP-SS-Code { 
--not impl ccitt identified-organization (4) etsi (0) mobileDomain (0) 
--not impl gsm-Network (1) modules (3) map-SS-Code (15) version3 (3)} 
--not impl ; 
--not impl 
--not impl 
-- supplementary service handling operations 
--not impl 
--not impl RegisterSS ::= OPERATION 
--Timer m 
--not impl ARGUMENT 
--not impl registerSS-Arg RegisterSS-Arg 
--not impl RESULT 
--not impl ss-Info SS-Info 
-- optional 
--not impl ERRORS { 
--not impl SystemFailure, 
--not impl DataMissing, 
--not impl UnexpectedDataValue, 
--not impl BearerServiceNotProvisioned, 
--not impl TeleserviceNotProvisioned, 
--not impl CallBarred, 
--not impl IllegalSS-Operation, 
--not impl SS-ErrorStatus, 
--not impl SS-Incompatibility} 
--not impl 
--not impl EraseSS ::= OPERATION 
--Timer m 
--not impl ARGUMENT 
--not impl ss-ForBS SS-ForBS-Code 
--not impl RESULT 
--not impl ss-Info SS-Info 
-- optional 
--not impl ERRORS { 
--not impl SystemFailure, 
--not impl DataMissing, 
--not impl UnexpectedDataValue, 
--not impl BearerServiceNotProvisioned, 
--not impl TeleserviceNotProvisioned, 
--not impl CallBarred, 
--not impl IllegalSS-Operation, 
--not impl SS-ErrorStatus 
--not impl } 
--not impl 
--not impl ActivateSS ::= OPERATION 
--Timer m 
--not impl ARGUMENT 
--not impl ss-ForBS SS-ForBS-Code 
--not impl RESULT 
--not impl ss-Info SS-Info 
-- optional 
--not impl ERRORS { 
--not impl SystemFailure, 
--not impl DataMissing, 
--not impl UnexpectedDataValue, 
--not impl BearerServiceNotProvisioned, 
--not impl TeleserviceNotProvisioned, 
--not impl CallBarred, 
--not impl IllegalSS-Operation, 
--not impl SS-ErrorStatus, 
--not impl SS-SubscriptionViolation, 
--not impl SS-Incompatibility, 
--not impl NegativePW-Check, 
--not impl NumberOfPW-AttemptsViolation} 
--not impl 
--not impl DeactivateSS ::= OPERATION 
--Timer m 
--not impl ARGUMENT 
--not impl ss-ForBS SS-ForBS-Code 
--not impl RESULT 
--not impl ss-Info SS-Info 
-- optional 
--not impl ERRORS { 
--not impl SystemFailure, 
--not impl DataMissing, 
--not impl UnexpectedDataValue, 
--not impl BearerServiceNotProvisioned, 
--not impl TeleserviceNotProvisioned, 
--not impl CallBarred, 
--not impl IllegalSS-Operation, 
--not impl SS-ErrorStatus, 
--not impl SS-SubscriptionViolation, 
--not impl NegativePW-Check, 
--not impl NumberOfPW-AttemptsViolation} 
--not impl 
--not impl InterrogateSS ::= OPERATION 
--Timer m 
--not impl ARGUMENT 
--not impl ss-ForBS SS-ForBS-Code 
--not impl RESULT 
--not impl interrogateSS-Res InterrogateSS-Res 
--not impl ERRORS { 
--not impl SystemFailure, 
--not impl DataMissing, 
--not impl UnexpectedDataValue, 
--not impl BearerServiceNotProvisioned, 
--not impl TeleserviceNotProvisioned, 
--not impl CallBarred, 
--not impl IllegalSS-Operation, 
--not impl SS-NotAvailable} 
--not impl 
--not impl ProcessUnstructuredSS-Request ::= OPERATION 
--Timer 10 minutes 
--not impl ARGUMENT 
--not impl ussd-Arg USSD-Arg 
--not impl RESULT 
--not impl ussd-Res USSD-Res 
--not impl ERRORS { 
--not impl SystemFailure, 
--not impl DataMissing, 
--not impl UnexpectedDataValue, 
--not impl UnknownAlphabet, 
--not impl CallBarred} 
--not impl 
--not impl UnstructuredSS-Request ::= OPERATION 
--Timer ml 
--not impl ARGUMENT 
--not impl ussd-Arg USSD-Arg 
--not impl RESULT 
--not impl ussd-Res USSD-Res 
-- optional 
--not impl ERRORS { 
--not impl SystemFailure, 
--not impl DataMissing, 
--not impl UnexpectedDataValue, 
--not impl AbsentSubscriber, 
--not impl IllegalSubscriber, 
--not impl IllegalEquipment, 
--not impl UnknownAlphabet, 
--not impl USSD-Busy} 
--not impl 
--not impl UnstructuredSS-Notify ::= OPERATION 
--Timer ml 
--not impl ARGUMENT 
--not impl ussd-Arg USSD-Arg 
--not impl RESULT 
--not impl ERRORS { 
--not impl SystemFailure, 
--not impl DataMissing, 
--not impl UnexpectedDataValue, 
--not impl AbsentSubscriber, 
--not impl IllegalSubscriber, 
--not impl IllegalEquipment, 
--not impl UnknownAlphabet, 
--not impl USSD-Busy} 
--not impl 
--not impl RegisterPassword ::= OPERATION 
--Timer ml 
--not impl ARGUMENT 
--not impl ss-Code SS-Code 
--not impl RESULT 
--not impl newPassword Password 
--not impl ERRORS { 
--not impl SystemFailure, 
--not impl DataMissing, 
--not impl UnexpectedDataValue, 
--not impl CallBarred, 
--not impl SS-SubscriptionViolation, 
--not impl PW-RegistrationFailure, 
--not impl NegativePW-Check, 
--not impl NumberOfPW-AttemptsViolation} 
--not impl LINKED { 
--not impl GetPassword} 
--not impl 
--not impl GetPassword ::= OPERATION 
--Timer m 
--not impl ARGUMENT 
--not impl guidanceInfo GuidanceInfo 
--not impl RESULT 
--not impl currentPassword Password 
--not impl 
--not impl END 
--not impl 

--------------------------------------------------------------------------------
--------------------------------------------------------------------------------
-------------------------------------------------------------------------------- 


-- Module ----------------------------------------------------------------------
--------------------------------------------------------------------------------
-- MAP Short Message Service Operations.
--------------------------------------------------------------------------------
--------------------------------------------------------------------------------

--not impl MAP-ShortMessageServiceOperations { 
--not impl ccitt identified-organization (4) etsi (0) mobileDomain (0) 
--not impl gsm-Network (1) modules (3) map-ShortMessageServiceOperations (9) 
--not impl version3 (3)} 
--not impl 
--not impl DEFINITIONS 
--not impl 
--not impl ::= 
--not impl 
--not impl BEGIN 
--not impl 
--not impl EXPORTS 
--not impl SendRoutingInfoForSM, 
--not impl MO-ForwardSM, 
--not impl MT-ForwardSM, 
--not impl ReportSM-DeliveryStatus, 
--not impl AlertServiceCentre, 
--not impl InformServiceCentre, 
--not impl ReadyForSM 
--not impl ; 
--not impl 
--not impl IMPORTS 
--not impl OPERATION 
--not impl FROM TCAPMessages { 
--not impl ccitt recommendation q 773 modules (2) messages (1) version2 (2)} 
--not impl 
--not impl SystemFailure, 
--not impl DataMissing, 
--not impl UnexpectedDataValue, 
--not impl FacilityNotSupported, 
--not impl UnknownSubscriber, 
--not impl UnidentifiedSubscriber, 
--not impl IllegalSubscriber, 
--not impl IllegalEquipment, 
--not impl TeleserviceNotProvisioned, 
--not impl AbsentSubscriber, 
--not impl CallBarred, 
--not impl SubscriberBusyForMT-SMS, 
--not impl SM-DeliveryFailure, 
--not impl MessageWaitingListFull, 
--not impl AbsentSubscriberSM 
--not impl FROM MAP-Errors { 
--not impl ccitt identified-organization (4) etsi (0) mobileDomain (0) 
--not impl gsm-Network (1) modules (3) map-Errors (10) version3 (3)} 
--not impl 
--not impl RoutingInfoForSM-Arg, 
--not impl RoutingInfoForSM-Res, 
--not impl MO-ForwardSM-Arg, 
--not impl MO-ForwardSM-Res, 
--not impl MT-ForwardSM-Arg, 
--not impl MT-ForwardSM-Res, 
--not impl ReportSM-DeliveryStatusArg, 
--not impl ReportSM-DeliveryStatusRes, 
--not impl AlertServiceCentreArg, 
--not impl InformServiceCentreArg, 
--not impl ReadyForSM-Arg 
--not impl FROM MAP-SM-DataTypes { 
--not impl ccitt identified-organization (4) etsi (0) mobileDomain (0) 
--not impl gsm-Network (1) modules (3) map-SM-DataTypes (16) version3 (3)} 
--not impl 
--not impl 
--not impl 
--not impl ; 
--not impl 
--not impl 
--not impl SendRoutingInfoForSM ::= OPERATION 
--Timer m 
--not impl ARGUMENT 
--not impl routingInfoForSM-Arg RoutingInfoForSM-Arg 
--not impl RESULT 
--not impl routingInfoForSM-Res RoutingInfoForSM-Res 
--not impl ERRORS { 
--not impl SystemFailure, 
--not impl DataMissing, 
--not impl UnexpectedDataValue, 
--not impl FacilityNotSupported, 
--not impl UnknownSubscriber, 
--not impl TeleserviceNotProvisioned, 
--not impl CallBarred, 
--not impl AbsentSubscriberSM} 
--not impl 
--not impl MO-ForwardSM ::= OPERATION 
--Timer ml 
--not impl ARGUMENT 
--not impl mo-forwardSM-Arg MO-ForwardSM-Arg 
--not impl RESULT 
--not impl mo-forwardSM-Res MO-ForwardSM-Res 
--not impl 
-- optional 
--not impl ERRORS { 
--not impl SystemFailure, 
--not impl UnexpectedDataValue, 
--not impl FacilityNotSupported, 
--not impl SM-DeliveryFailure} 
--not impl 
--not impl MT-ForwardSM ::= OPERATION 
--Timer ml 
--not impl ARGUMENT 
--not impl mt-forwardSM-Arg MT-ForwardSM-Arg 
--not impl RESULT 
--not impl mt-forwardSM-Res MT-ForwardSM-Res 
-- optional 
--not impl ERRORS { 
--not impl SystemFailure, 
--not impl DataMissing, 
--not impl UnexpectedDataValue, 
--not impl FacilityNotSupported, 
--not impl UnidentifiedSubscriber, 
--not impl IllegalSubscriber, 
--not impl IllegalEquipment, 
--not impl SubscriberBusyForMT-SMS, 
--not impl SM-DeliveryFailure, 
--not impl AbsentSubscriberSM} 
--not impl 
--not impl ReportSM-DeliveryStatus ::= OPERATION 
--Timer s 
--not impl ARGUMENT 
--not impl reportSM-DeliveryStatusArg ReportSM-DeliveryStatusArg 
--not impl RESULT 
--not impl reportSM-DeliveryStatusRes ReportSM-DeliveryStatusRes 
-- optional 
--not impl ERRORS { 
--not impl DataMissing, 
--not impl UnexpectedDataValue, 
--not impl UnknownSubscriber, 
--not impl MessageWaitingListFull} 
--not impl 
--not impl AlertServiceCentre ::= OPERATION 
--Timer s 
--not impl ARGUMENT 
--not impl alertServiceCentreArg AlertServiceCentreArg 
--not impl RESULT 
--not impl ERRORS { 
--not impl SystemFailure, 
--not impl DataMissing, 
--not impl UnexpectedDataValue} 
--not impl 
--not impl InformServiceCentre ::= OPERATION 
--Timer s 
--not impl ARGUMENT 
--not impl informServiceCentreArg InformServiceCentreArg 
--not impl 
--not impl ReadyForSM ::= OPERATION 
--Timer m 
--not impl ARGUMENT 
--not impl readyForSM-Arg ReadyForSM-Arg 
--not impl RESULT 
--not impl ERRORS { 
--not impl DataMissing, 
--not impl UnexpectedDataValue, 
--not impl FacilityNotSupported, 
--not impl UnknownSubscriber} 
--not impl 
--not impl END 
--not impl 

--------------------------------------------------------------------------------
--------------------------------------------------------------------------------
-------------------------------------------------------------------------------- 


-- Module ----------------------------------------------------------------------
--------------------------------------------------------------------------------
-- MAP Errors.
--------------------------------------------------------------------------------
--------------------------------------------------------------------------------

--not impl MAP-Errors { 
--not impl ccitt identified-organization (4) etsi (0) mobileDomain (0) 
--not impl gsm-Network (1) modules (3) map-Errors (10) version3 (3)} 
--not impl 
--not impl DEFINITIONS 
--not impl 
--not impl ::= 
--not impl 
--not impl BEGIN 
--not impl 
--not impl EXPORTS 
--not impl 
-- generic errors 
--not impl SystemFailure, 
--not impl DataMissing, 
--not impl UnexpectedDataValue, 
--not impl FacilityNotSupported, 
--not impl 
-- identification and numbering errors 
--not impl UnknownSubscriber, 
--not impl NumberChanged, 
--not impl UnknownMSC, 
--not impl UnidentifiedSubscriber, 
--not impl UnknownEquipment, 
--not impl 
-- subscription errors 
--not impl RoamingNotAllowed, 
--not impl IllegalSubscriber, 
--not impl IllegalEquipment, 
--not impl BearerServiceNotProvisioned, 
--not impl TeleserviceNotProvisioned, 
--not impl 
-- handover errors 
--not impl NoHandoverNumberAvailable, 
--not impl SubsequentHandoverFailure, 
--not impl 
-- operation and maintenance errors 
--not impl TracingBufferFull, 
--not impl 
-- call handling errors 
--not impl OR-NotAllowed, 
--not impl NoRoamingNumberAvailable, 
--not impl BusySubscriber, 
--not impl NoSubscriberReply, 
--not impl AbsentSubscriber, 
--not impl CallBarred, 
--not impl ForwardingViolation, 
--not impl ForwardingFailed, 
--not impl CUG-Reject, 
--not impl 
-- any time interrogation errors 
--not impl ATI-NotAllowed, 
--not impl 
-- supplementary service errors 
--not impl IllegalSS-Operation, 
--not impl SS-ErrorStatus, 
--not impl SS-NotAvailable, 
--not impl SS-SubscriptionViolation, 
--not impl SS-Incompatibility, 
--not impl UnknownAlphabet, 
--not impl USSD-Busy, 
--not impl PW-RegistrationFailure, 
--not impl NegativePW-Check, 
--not impl NumberOfPW-AttemptsViolation, 
--not impl 
-- short message service errors 
--not impl SubscriberBusyForMT-SMS, 
--not impl SM-DeliveryFailure, 
--not impl MessageWaitingListFull, 
--not impl AbsentSubscriberSM 
--not impl ; 
--not impl 
--not impl IMPORTS 
--not impl ERROR 
--not impl FROM TCAPMessages { 
--not impl ccitt recommendation q 773 modules (2) messages (1) version2 (2)} 
--not impl 
--not impl SS-Status 
--not impl FROM MAP-SS-DataTypes { 
--not impl ccitt identified-organization (4) etsi (0) mobileDomain (0) 
--not impl gsm-Network (1) modules (3) map-SS-DataTypes (14) version3 (3)} 
--not impl 
--not impl SS-IncompatibilityCause, 
--not impl PW-RegistrationFailureCause, 
--not impl SM-DeliveryFailureCause, 
--not impl SystemFailureParam, 
--not impl DataMissingParam, 
--not impl UnexpectedDataParam, 
--not impl FacilityNotSupParam, 
--not impl UnknownSubscriberParam, 
--not impl NumberChangedParam, 
--not impl UnidentifiedSubParam, 
--not impl RoamingNotAllowedParam, 
--not impl IllegalSubscriberParam, 
--not impl IllegalEquipmentParam, 
--not impl BearerServNotProvParam, 
--not impl TeleservNotProvParam, 
--not impl TracingBufferFullParam, 
--not impl NoRoamingNbParam, 
--not impl OR-NotAllowedParam, 
--not impl AbsentSubscriberParam, 
--not impl BusySubscriberParam, 
--not impl NoSubscriberReplyParam, 
--not impl CallBarredParam, 
--not impl ForwardingViolationParam, 
--not impl ForwardingFailedParam, 
--not impl CUG-RejectParam, 
--not impl ATI-NotAllowedParam, 
--not impl SubBusyForMT-SMS-Param, 
--not impl MessageWaitListFullParam, 
--not impl AbsentSubscriberSM-Param 
--not impl 
--not impl FROM MAP-ER-DataTypes { 
--not impl ccitt identified-organization (4) etsi (0) mobileDomain (0) 
--not impl gsm-Network (1) modules (3) map-ER-DataTypes (17) version3 (3)} 
--not impl ; 
--not impl 
--not impl 
-- generic errors 
--not impl 
--not impl SystemFailure ::= ERROR 
--not impl PARAMETER 
--not impl systemFailureParam SystemFailureParam 
-- optional 
--not impl 
--not impl DataMissing ::= ERROR 
--not impl PARAMETER 
--not impl dataMissingParam DataMissingParam 
-- optional 
-- dataMissingParam must not be used in version <3 
--not impl 
--not impl UnexpectedDataValue ::= ERROR 
--not impl PARAMETER 
--not impl unexpectedDataParam UnexpectedDataParam 
-- optional 
-- unexpectedDataParam must not be used in version <3 
--not impl 
--not impl FacilityNotSupported ::= ERROR 
--not impl PARAMETER 
--not impl facilityNotSupParam FacilityNotSupParam 
-- optional 
-- facilityNotSupParam must not be used in version <3 
--not impl 
--not impl 
-- identification and numbering errors 
--not impl 
--not impl UnknownSubscriber ::= ERROR 
--not impl PARAMETER 
--not impl unknownSubscriberParam UnknownSubscriberParam 
-- optional 
-- unknownSubscriberParam must not be used in version <3 
--not impl 
--not impl NumberChanged ::= ERROR 
--not impl PARAMETER 
--not impl numberChangedParam NumberChangedParam 
-- optional 
--not impl 
--not impl 
--not impl UnknownMSC ::= ERROR 
--not impl 
--not impl UnidentifiedSubscriber ::= ERROR 
--not impl PARAMETER 
--not impl unidentifiedSubParam UnidentifiedSubParam 
-- optional 
-- unidentifiedSubParam must not be used in version <3 
--not impl 
--not impl UnknownEquipment ::= ERROR 
--not impl 
--not impl 
-- subscription errors 
--not impl 
--not impl RoamingNotAllowed ::= ERROR 
--not impl PARAMETER 
--not impl roamingNotAllowedParam RoamingNotAllowedParam 
--not impl 
--not impl IllegalSubscriber ::= ERROR 
--not impl PARAMETER 
--not impl illegalSubscriberParam IllegalSubscriberParam 
-- optional 
-- illegalSubscriberParam must not be used in version <3 
--not impl 
--not impl IllegalEquipment ::= ERROR 
--not impl PARAMETER 
--not impl illegalEquipmentParam IllegalEquipmentParam 
-- optional 
-- illegalEquipmentParam must not be used in version <3 
--not impl 
--not impl BearerServiceNotProvisioned ::= ERROR 
--not impl PARAMETER 
--not impl bearerServNotProvParam BearerServNotProvParam 
-- optional 
-- bearerServNotProvParam must not be used in version <3 
--not impl 
--not impl TeleserviceNotProvisioned ::= ERROR 
--not impl PARAMETER 
--not impl teleservNotProvParam TeleservNotProvParam 
-- optional 
-- teleservNotProvParam must not be used in version <3 
--not impl 
--not impl 
-- handover errors 
--not impl 
--not impl NoHandoverNumberAvailable ::= ERROR 
--not impl 
--not impl SubsequentHandoverFailure ::= ERROR 
--not impl 
--not impl 
-- operation and maintenance errors 
--not impl 
--not impl TracingBufferFull ::= ERROR 
--not impl PARAMETER 
--not impl tracingBufferFullParam TracingBufferFullParam 
-- optional 
--not impl 
--not impl 
-- call handling errors 
--not impl 
--not impl NoRoamingNumberAvailable ::= ERROR 
--not impl PARAMETER 
--not impl noRoamingNbParam NoRoamingNbParam 
-- optional 
--not impl 
--not impl AbsentSubscriber ::= ERROR 
--not impl PARAMETER 
--not impl absentSubscriberParam AbsentSubscriberParam 
-- optional 
--not impl 
-- absentSubscriberParam must not be used in version <3 
--not impl BusySubscriber ::= ERROR 
--not impl PARAMETER 
--not impl busySubscriberParam BusySubscriberParam 
-- optional 
--not impl 
--not impl NoSubscriberReply ::= ERROR 
--not impl PARAMETER 
--not impl noSubscriberReplyParam NoSubscriberReplyParam 
-- optional 
--not impl 
--not impl CallBarred ::= ERROR 
--not impl PARAMETER 
--not impl callBarredParam CallBarredParam 
-- optional 
--not impl 
--not impl ForwardingViolation ::= ERROR 
--not impl PARAMETER 
--not impl forwardingViolationParam ForwardingViolationParam 
-- optional 
--not impl 
--not impl ForwardingFailed ::= ERROR 
--not impl PARAMETER 
--not impl forwardingFailedParam ForwardingFailedParam 
-- optional 
--not impl 
--not impl CUG-Reject ::= ERROR 
--not impl PARAMETER 
--not impl cug-RejectParam CUG-RejectParam 
-- optional 
--not impl 
--not impl OR-NotAllowed ::= ERROR 
--not impl PARAMETER 
--not impl or-NotAllowedParam OR-NotAllowedParam 
-- optional 
--not impl 
--not impl 
-- any time interrogation errors 
--not impl ATI-NotAllowed ::= ERROR 
--not impl PARAMETER 
--not impl ati-NotAllowedParam ATI-NotAllowedParam 
-- optional 
--not impl 
--not impl 
-- supplementary service errors 
--not impl 
--not impl IllegalSS-Operation ::= ERROR 
--not impl 
--not impl SS-ErrorStatus ::= ERROR 
--not impl PARAMETER 
--not impl ss-Status SS-Status 
-- optional 
--not impl 
--not impl SS-NotAvailable ::= ERROR 
--not impl 
--not impl SS-SubscriptionViolation ::= ERROR 
--not impl 
--not impl SS-Incompatibility ::= ERROR 
--not impl PARAMETER 
--not impl ss-IncompatibilityCause SS-IncompatibilityCause 
-- optional 
--not impl 
--not impl UnknownAlphabet ::= ERROR 
--not impl 
--not impl USSD-Busy ::= ERROR 
--not impl 
--not impl PW-RegistrationFailure ::= ERROR 
--not impl PARAMETER 
--not impl pw-RegistrationFailureCause PW-RegistrationFailureCause 
--not impl 
--not impl NegativePW-Check ::= ERROR 
--not impl 
--not impl NumberOfPW-AttemptsViolation ::= ERROR 
--not impl 
--not impl 
-- short message service errors 
--not impl 
--not impl SubscriberBusyForMT-SMS ::= ERROR 
--not impl PARAMETER 
--not impl subBusyForMT-SMS-Param SubBusyForMT-SMS-Param 
-- optional 
--not impl 
--not impl SM-DeliveryFailure ::= ERROR 
--not impl PARAMETER 
--not impl sm-DeliveryFailureCause SM-DeliveryFailureCause 
--not impl 
--not impl MessageWaitingListFull ::= ERROR 
--not impl PARAMETER 
--not impl messageWaitListFullParam MessageWaitListFullParam 
-- optional 
--not impl 
--not impl 
--not impl AbsentSubscriberSM ::= ERROR 
--not impl PARAMETER 
--not impl absentSubscriberSM-Param AbsentSubscriberSM-Param 
-- optional 
--not impl 
--not impl END 
--not impl 

--------------------------------------------------------------------------------
--------------------------------------------------------------------------------
-------------------------------------------------------------------------------- 


-- Module ----------------------------------------------------------------------
--------------------------------------------------------------------------------
-- MAP MS Data Types.
--------------------------------------------------------------------------------
--------------------------------------------------------------------------------

--not used MAP-MS-DataTypes { 
--not used ccitt identified-organization (4) etsi (0) mobileDomain (0) 
--not used gsm-Network (1) modules (3) map-MS-DataTypes (11) version3 (3)} 
--not used 
--not used DEFINITIONS 
--not used 
--not used IMPLICIT TAGS 
--not used 
--not used ::= 
--not used 
--not used BEGIN 
--not used 
--not used EXPORTS 
--not used 
-- location registration types 
--not used UpdateLocationArg, 
--not used UpdateLocationRes, 
--not used CancelLocationArg, 
--not used PurgeMS-Arg, 
--not used SendIdentificationRes, 
--not used 
-- handover types 
--not used PrepareHO-Arg, 
--not used PrepareHO-Res, 
--not used PrepareSubsequentHO-Arg, 
--not used 
-- authentication management types 
--not used SendAuthenticationInfoArg, 
--not used SendAuthenticationInfoRes, 
--not used 
-- security management types 
--not used EquipmentStatus, 
--not used 
-- subscriber management types 
--not used InsertSubscriberDataArg, 
--not used InsertSubscriberDataRes, 
--not used DeleteSubscriberDataArg, 
--not used DeleteSubscriberDataRes, 
--not used SubscriberData, 
--not used ODB-Data, 
--not used SubscriberStatus, 
--not used ZoneCodeList, 
--not used maxNumOfZoneCodes, 
--not used O-CSI, 
--not used ServiceKey, 
--not used DefaultCallHandling, 
--not used SupportedCamelPhases, 
--not used maxNumOfCamelTDPData, 
--not used CUG-Index, 
--not used CUG-Interlock, 
--not used InterCUG-Restrictions, 
--not used IntraCUG-Options, 
--not used 
-- fault recovery types 
--not used ResetArg, 
--not used RestoreDataArg, 
--not used RestoreDataRes, 
--not used 
-- subscriber information enquiry types 
--not used ProvideSubscriberInfoArg, 
--not used ProvideSubscriberInfoRes, 
--not used SubscriberInfo, 
--not used LocationInformation, 
--not used SubscriberState, 
--not used 
-- any time information enquiry types 
--not used AnyTimeInterrogationArg, 
--not used AnyTimeInterrogationRes 
--not used 
--not used ; 
--not used 
--not used IMPORTS 
--not used maxNumOfSS, 
--not used SS-SubscriptionOption, 
--not used SS-List 
--not used FROM MAP-SS-DataTypes { 
--not used ccitt identified-organization (4) etsi (0) mobileDomain (0) 
--not used gsm-Network (1) modules (3) map-SS-DataTypes (14) version3 (3)} 
--not used 
--not used SS-Code 
--not used FROM MAP-SS-Code { 
--not used ccitt identified-organization (4) etsi (0) mobileDomain (0) 
--not used gsm-Network (1) modules (3) map-SS-Code (15) version3 (3)} 
--not used 
--not used Ext-BearerServiceCode 
--not used FROM MAP-BS-Code { 
--not used ccitt identified-organization (4) etsi (0) mobileDomain (0) 
--not used gsm-Network (1) modules (3) map-BS-Code (20) version3 (3)} 
--not used 
--not used Ext-TeleserviceCode 
--not used FROM MAP-TS-Code { 
--not used ccitt identified-organization (4) etsi (0) mobileDomain (0) 
--not used gsm-Network (1) modules (3) map-TS-Code (19) version3 (3)} 
--not used 
--not used 
--not used ISDN-AddressString, 
--not used ISDN-SubaddressString, 
--not used ExternalSignalInfo, 
--not used IMSI, 
--not used HLR-List, 
--not used LMSI, 
--not used GlobalCellId, 
--not used CellIdOrLAI, 
--not used Ext-BasicServiceCode 
--not used 
--not used FROM MAP-CommonDataTypes { 
--not used ccitt identified-organization (4) etsi (0) mobileDomain (0) 
--not used gsm-Network (1) modules (3) map-CommonDataTypes (18) version3 (3)} 
--not used 
--not used ExtensionContainer 
--not used FROM MAP-ExtensionDataTypes { 
--not used ccitt identified-organization (4) etsi (0) mobileDomain (0) 
--not used gsm-Network (1) modules (3) map-ExtensionDataTypes (21) version3 (3)} 
--not used 
--not used ; 
--not used 
--not used 
-- location registration types 


UpdateLocationArg ::= SEQUENCE {
    imsi            IMSI,

    msc-Number  [1] ISDN-AddressString,
    vlr-Number  ISDN-AddressString,
    lmsi            [10] LMSI   OPTIONAL,
    extensionContainer  ExtensionContainer  OPTIONAL,
    ... }

UpdateLocationRes ::= SEQUENCE { 
hlr-Number ISDN-AddressString, 
extensionContainer ExtensionContainer OPTIONAL, 
... } 


CancelLocationArg ::= CHOICE { 
imsi IMSI, 
imsi-WithLMSI IMSI-WithLMSI} 

PurgeMS-Arg ::= SEQUENCE { 
imsi IMSI, 
vlr-Number ISDN-AddressString, 
...} 

IMSI-WithLMSI ::= SEQUENCE { 
imsi IMSI, 
lmsi LMSI, 
-- a special value 00000000 indicates that the LMSI is not in use 
...} 

SendIdentificationRes ::= SEQUENCE { 
imsi IMSI, 
authenticationSetList AuthenticationSetList OPTIONAL, 
...} 

AuthenticationSetList ::= SEQUENCE SIZE (1..5) OF 
AuthenticationSet 

AuthenticationSet ::= SEQUENCE { 
rand RAND, 
sres SRES, 
kc Kc, 
...} 

RAND ::= OCTET STRING (SIZE (16)) 

SRES ::= OCTET STRING (SIZE (4)) 

Kc ::= OCTET STRING (SIZE (8)) 

-- handover types 

PrepareHO-Arg ::= SEQUENCE { 
targetCellId GlobalCellId OPTIONAL, 
ho-NumberNotRequired NULL OPTIONAL, 
bss-APDU ExternalSignalInfo OPTIONAL, 
...} 

PrepareHO-Res ::= SEQUENCE { 
handoverNumber ISDN-AddressString OPTIONAL, 
bss-APDU ExternalSignalInfo OPTIONAL, 
...} 

PrepareSubsequentHO-Arg ::= SEQUENCE { 
targetCellId GlobalCellId, 
targetMSC-Number ISDN-AddressString, 
bss-APDU ExternalSignalInfo, 
...} 

-- authentication management types 

SendAuthenticationInfoArg ::= IMSI 

SendAuthenticationInfoRes ::= AuthenticationSetList 


-- security management types 

EquipmentStatus ::= ENUMERATED { 
whiteListed (0), 
blackListed (1), 
greyListed (2)} 


-- subscriber management types 

InsertSubscriberDataArg ::= SEQUENCE { 
imsi [0] IMSI OPTIONAL, 
COMPONENTS OF SubscriberData, 
extensionContainer [14] ExtensionContainer OPTIONAL, 
...} 

SubscriberData ::= SEQUENCE { 
msisdn [1] ISDN-AddressString OPTIONAL, 
category [2] Category OPTIONAL, 
subscriberStatus [3] SubscriberStatus OPTIONAL, 
bearerServiceList [4] BearerServiceList OPTIONAL, 
-- The exception handling for reception of unsupported / not allocated 
-- bearerServiceCodes is defined in section 6.8.1 
teleserviceList [6] TeleserviceList OPTIONAL, 
-- The exception handling for reception of unsupported / not allocated 
-- teleserviceCodes is defined in section 6.8.1 
provisionedSS [7] Ext-SS-InfoList OPTIONAL, 
odb-Data [8] ODB-Data OPTIONAL, 
roamingRestrictionDueToUnsupportedFeature [9] NULL OPTIONAL, 
regionalSubscriptionData [10] ZoneCodeList OPTIONAL, 
vbsSubscriptionData [11] VBSDataList OPTIONAL, 
vgcsSubscriptionData [12] VGCSDataList OPTIONAL, 
vlrCamelSubscriptionInfo [13] VlrCamelSubscriptionInfo OPTIONAL 
} 

Category ::= OCTET STRING (SIZE (1)) 
-- The internal structure is defined in CCITT Rec Q.763. 

SubscriberStatus ::= ENUMERATED { 
serviceGranted (0), 
operatorDeterminedBarring (1)} 

BearerServiceList ::= SEQUENCE SIZE (1..maxNumOfBearerServices) OF 
Ext-BearerServiceCode 

maxNumOfBearerServices INTEGER ::= 50 

TeleserviceList ::= SEQUENCE SIZE (1..maxNumOfTeleservices) OF 
Ext-TeleserviceCode 

maxNumOfTeleservices INTEGER ::= 20 

ODB-Data ::= SEQUENCE { 
odb-GeneralData ODB-GeneralData, 
odb-HPLMN-Data ODB-HPLMN-Data OPTIONAL, 
extensionContainer ExtensionContainer OPTIONAL, 
...} 

ODB-GeneralData ::= BIT STRING { 
allOG-CallsBarred (0), 
internationalOGCallsBarred (1), 
internationalOGCallsNotToHPLMN-CountryBarred (2), 
interzonalOGCallsBarred (6), 
interzonalOGCallsNotToHPLMN-CountryBarred (7), 
interzonalOGCallsAndInternationalOGCallsNotToHPLMN-CountryBarred (8), 
premiumRateInformationOGCallsBarred (3), 
premiumRateEntertainementOGCallsBarred (4), 
ss-AccessBarred (5), 
allECT-Barred (9), 
chargeableECT-Barred (10), 
internationalECT-Barred (11), 
interzonalECT-Barred (12), 
doublyChargeableECT-Barred (13), 
multipleECT-Barred (14)} (SIZE (15..32)) 
-- exception handling: reception of unknown bit assignments in the 
-- ODB-GeneralData type shall be treated like unsupported ODB-GeneralData 

ODB-HPLMN-Data ::= BIT STRING { 
plmn-SpecificBarringType1 (0), 
plmn-SpecificBarringType2 (1), 
plmn-SpecificBarringType3 (2), 
plmn-SpecificBarringType4 (3)} (SIZE (4..32)) 
-- exception handling: reception of unknown bit assignments in the 
-- ODB-HPLMN-Data type shall be treated like unsupported ODB-HPLMN-Data 

Ext-SS-InfoList ::= SEQUENCE SIZE (1..maxNumOfSS) OF 
Ext-SS-Info 

Ext-SS-Info ::= CHOICE { 
forwardingInfo [0] Ext-ForwInfo, 
callBarringInfo [1] Ext-CallBarInfo, 
cug-Info [2] CUG-Info, 
ss-Data [3] Ext-SS-Data, 
emlpp-Info [4] EMLPP-Info} 

EMLPP-Info ::= SEQUENCE { 
maximumentitledPriority EMLPP-Priority, 
defaultPriority EMLPP-Priority, 
extensionContainer ExtensionContainer OPTIONAL, 
...} 

EMLPP-Priority ::= INTEGER (0..15) 
-- The mapping from the values A,B,0,1,2,3,4 to the integer-value is 
-- specified as follows where A is the highest and 4 is the lowest 
-- priority level 
-- the integer values 7-15 are spare and shall be mapped to value 4 

priorityLevelA EMLPP-Priority ::= 6 
priorityLevelB EMLPP-Priority ::= 5 
priorityLevel0 EMLPP-Priority ::= 0 
priorityLevel1 EMLPP-Priority ::= 1 
priorityLevel2 EMLPP-Priority ::= 2 
priorityLevel3 EMLPP-Priority ::= 3 
priorityLevel4 EMLPP-Priority ::= 4 
Ext-ForwInfo ::= SEQUENCE { 
ss-Code SS-Code, 
forwardingFeatureList Ext-ForwFeatureList, 
extensionContainer [0] ExtensionContainer OPTIONAL, 
...} 

Ext-ForwFeatureList ::= 
SEQUENCE SIZE (1..maxNumOfExt-BasicServiceGroups) OF 
Ext-ForwFeature 

Ext-ForwFeature ::= SEQUENCE { 
basicService Ext-BasicServiceCode OPTIONAL, 
ss-Status [4] Ext-SS-Status, 
forwardedToNumber [5] ISDN-AddressString OPTIONAL, 
forwardedToSubaddress [8] ISDN-SubaddressString OPTIONAL, 
forwardingOptions [6] Ext-ForwOptions OPTIONAL, 
noReplyConditionTime [7] Ext-NoRepCondTime OPTIONAL, 
extensionContainer [9] ExtensionContainer OPTIONAL, 
...} 

Ext-SS-Status ::= OCTET STRING (SIZE (1..5)) 

-- OCTET 1: 
-- 
-- bits 8765: 0000 (unused) 
-- bits 4321: Used to convey the "P bit","R bit","A bit" and "Q bit", 
-- representing supplementary service state information 
-- as defined in TS GSM 03.11 

-- bit 4: "Q bit" 

-- bit 3: "P bit" 

-- bit 2: "R bit" 

-- bit 1: "A bit" 

-- OCTETS 2-5: reserved for future use. They shall be discarded if 
-- received and not understood. 


Ext-ForwOptions ::= OCTET STRING (SIZE (1..5)) 

-- OCTET 1: 

-- bit 8: notification to forwarding party 
-- 0 no notification 
-- 1 notification 

-- bit 7: 0 (unused) 

-- bit 6: notification to calling party 
-- 0 no notification 
-- 1 notification 

-- bit 5: 0 (unused) 

-- bits 43: forwarding reason 
-- 00 ms not reachable 
-- 01 ms busy 
-- 10 no reply 
-- 11 unconditional 

-- bits 21: 00 (unused) 

-- OCTETS 2-5: reserved for future use. They shall be discarded if 
-- received and not understood. 

Ext-NoRepCondTime ::= INTEGER (1..100) 
-- Only values 5-30 are used. 
-- Values in the ranges 1-4 and 31-100 are reserved for future use 
-- If received: 
-- values 1-4 shall be mapped on to value 5 
-- values 31-100 shall be mapped on to value 30 

Ext-CallBarInfo ::= SEQUENCE { 
ss-Code SS-Code, 
callBarringFeatureList Ext-CallBarFeatureList, 
extensionContainer ExtensionContainer OPTIONAL, 
...} 

Ext-CallBarFeatureList ::= 
SEQUENCE SIZE (1..maxNumOfExt-BasicServiceGroups) OF 
Ext-CallBarringFeature 

Ext-CallBarringFeature ::= SEQUENCE { 
basicService Ext-BasicServiceCode OPTIONAL, 
ss-Status [4] Ext-SS-Status, 
extensionContainer ExtensionContainer OPTIONAL, 
...} 

CUG-Info ::= SEQUENCE { 
cug-SubscriptionList CUG-SubscriptionList, 
cug-FeatureList CUG-FeatureList OPTIONAL, 
extensionContainer [0] ExtensionContainer OPTIONAL, 
...} 

CUG-SubscriptionList ::= SEQUENCE SIZE (0..maxNumOfCUG) OF 
CUG-Subscription 

CUG-Subscription ::= SEQUENCE { 
cug-Index CUG-Index, 
cug-Interlock CUG-Interlock, 
intraCUG-Options IntraCUG-Options, 
basicServiceGroupList Ext-BasicServiceGroupList OPTIONAL, 
extensionContainer [0] ExtensionContainer OPTIONAL, 
...} 

CUG-Index ::= INTEGER (0..32767) 
-- The internal structure is defined in ETS 300 138. 

CUG-Interlock ::= OCTET STRING (SIZE (4)) 

IntraCUG-Options ::= ENUMERATED { 
noCUG-Restrictions (0), 
cugIC-CallBarred (1), 
cugOG-CallBarred (2)} 

maxNumOfCUG INTEGER ::= 10 

CUG-FeatureList ::= SEQUENCE SIZE (1..maxNumOfExt-BasicServiceGroups) OF 
CUG-Feature 

Ext-BasicServiceGroupList ::= SEQUENCE SIZE (1..maxNumOfExt-BasicServiceGroups) 
OF 
Ext-BasicServiceCode 

maxNumOfExt-BasicServiceGroups INTEGER ::= 32 

CUG-Feature ::= SEQUENCE { 
basicService Ext-BasicServiceCode OPTIONAL, 
preferentialCUG-Indicator CUG-Index OPTIONAL, 
interCUG-Restrictions InterCUG-Restrictions, 
extensionContainer ExtensionContainer OPTIONAL, 
...} 

InterCUG-Restrictions::= OCTET STRING (SIZE (1)) 

-- bits 876543: 000000 (unused) 
-- Exception handling: 
-- bits 876543 shall be ignored if received and not understood 

-- bits 21 
-- 00 CUG only facilities 
-- 01 CUG with outgoing access 
-- 10 CUG with incoming access 
-- 11 CUG with both outgoing and incoming access 
Ext-SS-Data ::= SEQUENCE { 
ss-Code SS-Code, 
ss-Status [4] Ext-SS-Status, 
ss-SubscriptionOption SS-SubscriptionOption OPTIONAL, 
basicServiceGroupList Ext-BasicServiceGroupList OPTIONAL, 
extensionContainer [5] ExtensionContainer OPTIONAL, 
...} 

ZoneCodeList ::= SEQUENCE SIZE (1..maxNumOfZoneCodes) 
OF ZoneCode 

ZoneCode ::= OCTET STRING (SIZE (2)) 
-- internal structure is defined in TS GSM 03.03 

maxNumOfZoneCodes INTEGER ::= 10 

InsertSubscriberDataRes ::= SEQUENCE { 
teleserviceList [1] TeleserviceList OPTIONAL, 
bearerServiceList [2] BearerServiceList OPTIONAL, 
ss-List [3] SS-List OPTIONAL, 
odb-GeneralData [4] ODB-GeneralData OPTIONAL, 
regionalSubscriptionResponse [5] 
RegionalSubscriptionResponse OPTIONAL, 
supportedCamelPhases [6] SupportedCamelPhases OPTIONAL, 
extensionContainer [7] ExtensionContainer OPTIONAL, 
...}

RegionalSubscriptionResponse ::= ENUMERATED {
-- Used before modification. 
-- msc-AreaRestricted (0), 
networkNode-AreaRestricted  (0),
tooManyZoneCodes (1), 
zoneCodesConflict (2), 
regionalSubscNotSupported (3)} 

DeleteSubscriberDataArg ::= SEQUENCE { 
imsi [0] IMSI, 
basicServiceList [1] BasicServiceList OPTIONAL, 
-- The exception handling for reception of unsupported / not allocated 
-- basicServiceCodes is defined in section 6.8.2 
ss-List [2] SS-List OPTIONAL, 
roamingRestrictionDueToUnsupportedFeature [4] NULL OPTIONAL, 
regionalSubscriptionIdentifier [5] ZoneCode OPTIONAL, 
vbsGroupIndication [7] NULL OPTIONAL, 
vgcsGroupIndication [8] NULL OPTIONAL, 
camelSubscriptionInfoWithdraw [9] NULL OPTIONAL, 
extensionContainer [6] ExtensionContainer OPTIONAL, 
...} 

BasicServiceList ::= SEQUENCE SIZE (1..maxNumOfBasicServices) OF 
Ext-BasicServiceCode 

maxNumOfBasicServices INTEGER ::= 70 

DeleteSubscriberDataRes ::= SEQUENCE { 
regionalSubscriptionResponse [0] 
RegionalSubscriptionResponse OPTIONAL, 
extensionContainer ExtensionContainer OPTIONAL, 
...} 

VlrCamelSubscriptionInfo ::= SEQUENCE { 
o-CSI [0] O-CSI OPTIONAL, 
extensionContainer [1] ExtensionContainer OPTIONAL, 
...} 

O-CSI ::= SEQUENCE { 
o-BcsmCamelTDPDataList O-BcsmCamelTDPDataList, 
extensionContainer ExtensionContainer OPTIONAL, 
...} 

O-BcsmCamelTDPDataList ::= SEQUENCE SIZE (1..maxNumOfCamelTDPData) OF 
O-BcsmCamelTDPData 

maxNumOfCamelTDPData INTEGER ::= 10 

O-BcsmCamelTDPData ::= SEQUENCE { 
o-BcsmTriggerDetectionPoint O-BcsmTriggerDetectionPoint, 
serviceKey ServiceKey, 
gsmSCF-Address [0] ISDN-AddressString, 
defaultCallHandling [1] DefaultCallHandling, 
extensionContainer [2] ExtensionContainer OPTIONAL, 
...} 

ServiceKey ::= INTEGER (0..2147483647) 

O-BcsmTriggerDetectionPoint ::= ENUMERATED { 
collectedInfo (2), 
... } 
-- exception handling: 
-- For O-BcsmCamelTDPData sequences containing this parameter with any 
-- other value than the ones listed the receiver shall ignore the whole 
-- O-BcsmCamelTDPDatasequence. 

DefaultCallHandling ::= ENUMERATED { 
continueCall (0) , 
releaseCall (1) , 
...} 
-- exception handling: 
-- reception of values in range 2-31 shall be treated as "continueCall" 
-- reception of values greater than 31 shall be treated as "releaseCall" 

SupportedCamelPhases ::= BIT STRING { 
phase1 (0),
phase2 (1) } (SIZE (1..16)) 


-- fault recovery types 

ResetArg ::= SEQUENCE { 
hlr-Number ISDN-AddressString, 
hlr-List HLR-List OPTIONAL, 
...} 

RestoreDataArg ::= SEQUENCE { 
imsi IMSI, 
lmsi LMSI OPTIONAL, 
extensionContainer ExtensionContainer OPTIONAL, 
...} 

RestoreDataRes ::= SEQUENCE { 
hlr-Number ISDN-AddressString, 
msNotReachable NULL OPTIONAL, 
extensionContainer ExtensionContainer OPTIONAL, 
...} 

-- VBS/VGCS types 
VBSDataList ::= SEQUENCE SIZE (1..maxNumOfVBSGroupIds) 
OF VoiceBroadcastData 

VGCSDataList ::= SEQUENCE SIZE (1..maxNumOfVGCSGroupIds) 
OF VoiceGroupCallData 

maxNumOfVBSGroupIds INTEGER ::= 50 

maxNumOfVGCSGroupIds INTEGER ::= 50 

VoiceGroupCallData ::= SEQUENCE { 
groupId GroupId, 
extensionContainer ExtensionContainer OPTIONAL, 
...} 

VoiceBroadcastData ::= SEQUENCE { 
groupid GroupId, 
broadcastInitEntitlement NULL OPTIONAL, 
extensionContainer ExtensionContainer OPTIONAL, 
...} 

GroupId ::= OCTET STRING (SIZE (3)) 
-- Refers to the Group Identification as specified in GSM TS 03.03 
-- and 03.68/ 03.69 

-- provide subscriber info types 

ProvideSubscriberInfoArg ::= SEQUENCE { 
imsi [0] IMSI, 
lmsi [1] LMSI OPTIONAL, 
requestedInfo [2] RequestedInfo, 
extensionContainer [3] ExtensionContainer OPTIONAL, 
...} 

ProvideSubscriberInfoRes ::= SEQUENCE { 
subscriberInfo SubscriberInfo, 
extensionContainer ExtensionContainer OPTIONAL, 
...} 

SubscriberInfo ::= SEQUENCE { 
locationInformation [0] LocationInformation OPTIONAL, 
subscriberState [1] SubscriberState OPTIONAL, 
extensionContainer [2] ExtensionContainer OPTIONAL, 
...} 

RequestedInfo ::= SEQUENCE { 
locationInformation [0] NULL OPTIONAL, 
subscriberState [1] NULL OPTIONAL, 
extensionContainer [2] ExtensionContainer OPTIONAL, 
...} 

LocationInformation ::= SEQUENCE { 
ageOfLocationInformation AgeOfLocationInformation OPTIONAL, 
geographicalInformation [0] GeographicalInformation OPTIONAL, 
vlr-number [1] ISDN-AddressString OPTIONAL, 
locationNumber [2] LocationNumber OPTIONAL, 
cellIdOrLAI [3] CellIdOrLAI OPTIONAL, 
extensionContainer [4] ExtensionContainer OPTIONAL, 
...} 

AgeOfLocationInformation ::= INTEGER (0..32767) 
-- the value represents the elapsed time in minutes since the last 
-- network contact of the mobile station (i.e. the actuality of the 
-- location information). 
-- value “0” indicates that the MS is currently in contact with the 
-- network 
-- value “32767” indicates that the location information is at least 
-- 32767 minutes old 

GeographicalInformation ::= OCTET STRING (SIZE (8)) 
-- Refers to geographical Information defined in GSM 03.32. 
-- Only the description of an ellipsoid point with uncertainty circle 
--as specified in GSM 03.32 is allowed to be used 
-- The internal structure according to GSM 03.32 is as follows: 
-- Type of shape (ellipsoid point with uncertainty circle) 1 octet 
-- Degrees of Latitude 3 octets 
-- Degrees of Longitude 3 octets 
-- Uncertainty code 1 octet 

LocationNumber ::= OCTET STRING (SIZE (2..10)) 
-- the internal structure is defined in CCITT Rec Q.763 

SubscriberState ::= CHOICE { 
assumedIdle [0] NULL, 
camelBusy [1] NULL, 
netDetNotReachable NotReachableReason, 
notProvidedFromVLR [2] NULL} 

NotReachableReason ::= ENUMERATED { 
msPurged (0), 
imsiDetached (1), 
restrictedArea (2), 
notRegistered (3)} 

-- any time interrogation info types 

AnyTimeInterrogationArg ::= SEQUENCE { 
subscriberIdentity [0] SubscriberIdentity, 
requestedInfo [1] RequestedInfo, 
gsmSCF-Address [3] ISDN-AddressString, 
extensionContainer [2] ExtensionContainer OPTIONAL, 
...} 

AnyTimeInterrogationRes ::= SEQUENCE { 
subscriberInfo SubscriberInfo, 
extensionContainer ExtensionContainer OPTIONAL, 
...} 

SubscriberIdentity ::= CHOICE { 
imsi [0] IMSI, 
msisdn [1] ISDN-AddressString 
} 

--not used 
--not used END 
--not used 

--------------------------------------------------------------------------------
--------------------------------------------------------------------------------
--------------------------------------------------------------------------------


-- Module ----------------------------------------------------------------------
--------------------------------------------------------------------------------
-- MAP OM Data Types.
--------------------------------------------------------------------------------
--------------------------------------------------------------------------------

--not used MAP-OM-DataTypes { 
--not used ccitt identified-organization (4) etsi (0) mobileDomain (0) 
--not used gsm-Network (1) modules (3) map-OM-DataTypes (12) version3 (3)} 
--not used 
--not used DEFINITIONS 
--not used 
--not used IMPLICIT TAGS 
--not used 
--not used ::= 
--not used 
--not used BEGIN 
--not used 
--not used EXPORTS 
--not used ActivateTraceModeArg, 
--not used ActivateTraceModeRes, 
--not used DeactivateTraceModeArg, 
--not used DeactivateTraceModeRes 
--not used ; 
--not used 
--not used IMPORTS 
--not used AddressString, 
--not used IMSI 
--not used FROM MAP-CommonDataTypes { 
--not used ccitt identified-organization (4) etsi (0) mobileDomain (0) 
--not used gsm-Network (1) modules (3) map-CommonDataTypes (18) version3 (3)} 
--not used 
--not used ExtensionContainer 
--not used FROM MAP-ExtensionDataTypes { 
--not used ccitt identified-organization (4) etsi (0) mobileDomain (0) 
--not used gsm-Network (1) modules (3) map-ExtensionDataTypes (21) version3 (3)} 
--not used 
--not used 
--not used ; 
--not used 
--not used 


ActivateTraceModeArg ::= SEQUENCE { 
imsi [0] IMSI OPTIONAL, 
traceReference [1] TraceReference, 
traceType [2] TraceType, 
omc-Id [3] AddressString OPTIONAL, 
extensionContainer [4] ExtensionContainer OPTIONAL, 
...} 

TraceReference ::= OCTET STRING (SIZE (1..2)) 

TraceType ::= INTEGER 
(0..255) 
-- Trace types are fully defined in TS GSM 12.08. 

ActivateTraceModeRes ::= SEQUENCE { 
extensionContainer [0] ExtensionContainer OPTIONAL, 
...} 

DeactivateTraceModeArg ::= SEQUENCE { 
imsi [0] IMSI OPTIONAL, 
traceReference [1] TraceReference, 
extensionContainer [2] ExtensionContainer OPTIONAL, 
...} 

DeactivateTraceModeRes ::= SEQUENCE { 
extensionContainer [0] ExtensionContainer OPTIONAL, 
...} 

--not used 
--not used END 
--not used 

--------------------------------------------------------------------------------
--------------------------------------------------------------------------------
--------------------------------------------------------------------------------


-- Module ----------------------------------------------------------------------
--------------------------------------------------------------------------------
-- MAP CH Data Types.
--------------------------------------------------------------------------------
--------------------------------------------------------------------------------


--not used MAP-CH-DataTypes { 
--not used ccitt identified-organization (4) etsi (0) mobileDomain (0) 
--not used gsm-Network (1) modules (3) map-CH-DataTypes (13) version3 (3)} 
--not used 
--not used DEFINITIONS 
--not used 
--not used IMPLICIT TAGS 
--not used 
--not used ::= 
--not used 
--not used BEGIN 
--not used 
--not used EXPORTS 
--not used SendRoutingInfoArg, 
--not used SendRoutingInfoRes, 
--not used ProvideRoamingNumberArg, 
--not used ProvideRoamingNumberRes, 
--not used ResumeCallHandlingArg, 
--not used ResumeCallHandlingRes, 
--not used NumberOfForwarding, 
--not used SuppressionOfAnnouncement, 
--not used CallReferenceNumber 
--not used ; 
--not used 
--not used IMPORTS 
--not used maxNumOfCamelTDPData, 
--not used SubscriberInfo, 
--not used ServiceKey, 
--not used DefaultCallHandling, 
--not used SupportedCamelPhases, 
--not used CUG-Interlock, 
--not used O-CSI 
--not used FROM MAP-MS-DataTypes { 
--not used ccitt identified-organization (4) etsi (0) mobileDomain (0) 
--not used gsm-Network (1) modules (3) map-MS-DataTypes (11) version3 (3)} 
--not used 
--not used ForwardingOptions, 
--not used SS-List 
--not used FROM MAP-SS-DataTypes { 
--not used ccitt identified-organization (4) etsi (0) mobileDomain (0) 
--not used gsm-Network (1) modules (3) map-SS-DataTypes (14) version3 (3)} 
--not used 
--not used ISDN-AddressString, 
--not used ISDN-SubaddressString, 
--not used ExternalSignalInfo, 
--not used IMSI, 
--not used LMSI, 
--not used Ext-BasicServiceCode 
--not used FROM MAP-CommonDataTypes { 
--not used ccitt identified-organization (4) etsi (0) mobileDomain (0) 
--not used gsm-Network (1) modules (3) map-CommonDataTypes (18) version3 (3)} 
--not used 
--not used ExtensionContainer 
--not used FROM MAP-ExtensionDataTypes { 
--not used ccitt identified-organization (4) etsi (0) mobileDomain (0) 
--not used gsm-Network (1) modules (3) map-ExtensionDataTypes (21) version3 (3)} 
--not used ; 
--not used 
--not used 


CUG-CheckInfo ::= SEQUENCE { 
cug-Interlock CUG-Interlock, 
cug-OutgoingAccess NULL OPTIONAL, 
extensionContainer ExtensionContainer OPTIONAL, 
...} 

NumberOfForwarding ::= INTEGER (1..5) 

SendRoutingInfoArg ::= SEQUENCE { 
msisdn [0] ISDN-AddressString, 
cug-CheckInfo [1] CUG-CheckInfo OPTIONAL, 
numberOfForwarding [2] NumberOfForwarding OPTIONAL, 
interrogationType [3] InterrogationType, 
or-Interrogation [4] NULL OPTIONAL, 
or-Capability [5] OR-Phase OPTIONAL, 
gmsc-Address [6] ISDN-AddressString, 
callReferenceNumber [7] CallReferenceNumber OPTIONAL, 
forwardingReason [8] ForwardingReason OPTIONAL, 
basicServiceGroup [9] Ext-BasicServiceCode OPTIONAL, 
networkSignalInfo [10] ExternalSignalInfo OPTIONAL, 
camelInfo [11] CamelInfo OPTIONAL, 
suppressionOfAnnouncement [12] SuppressionOfAnnouncement OPTIONAL, 
extensionContainer [13] ExtensionContainer OPTIONAL, 
...} 

SuppressionOfAnnouncement ::= NULL 

InterrogationType ::= ENUMERATED { 
basicCall (0), 
forwarding (1)} 

OR-Phase ::= INTEGER (1..127) 

CallReferenceNumber ::= OCTET STRING (SIZE (1..8)) 

ForwardingReason ::= ENUMERATED { 
notReachable (0), 
busy (1), 
noReply (2)} 


SendRoutingInfoRes ::=  SEQUENCE { 
imsi [9] IMSI OPTIONAL, 
-- IMSI must be present if SendRoutingInfoRes is not segmented. 
-- If the TC-Result-NL segmentation option is taken the IMSI must be 
-- present in one segmented transmission of SendRoutingInfoRes. 
extendedRoutingInfo ExtendedRoutingInfo OPTIONAL, 
cug-CheckInfo [3] CUG-CheckInfo OPTIONAL, 
cugSubscriptionFlag [6] NULL OPTIONAL, 
subscriberInfo [7] SubscriberInfo OPTIONAL, 
ss-List [1] SS-List OPTIONAL, 
basicService [5] Ext-BasicServiceCode OPTIONAL, 
forwardingInterrogationRequired [4] NULL OPTIONAL, 
vmsc-Address [2] ISDN-AddressString OPTIONAL, 
extensionContainer [0] ExtensionContainer OPTIONAL, 
...} 

RoutingInfo ::= CHOICE { 
roamingNumber ISDN-AddressString, 
forwardingData ForwardingData} 

ForwardingData ::= SEQUENCE { 
forwardedToNumber [5] ISDN-AddressString OPTIONAL, 
forwardedToSubaddress [4] ISDN-SubaddressString OPTIONAL, 
forwardingOptions [6] ForwardingOptions OPTIONAL, 
extensionContainer [7] ExtensionContainer OPTIONAL, 
...} 

ProvideRoamingNumberArg ::= SEQUENCE { 
imsi [0] IMSI, 
msc-Number [1] ISDN-AddressString, 
msisdn [2] ISDN-AddressString OPTIONAL, 
lmsi [4] LMSI OPTIONAL, 
gsm-BearerCapability [5] ExternalSignalInfo OPTIONAL, 
networkSignalInfo [6] ExternalSignalInfo OPTIONAL, 
suppressionOfAnnouncement [7] SuppressionOfAnnouncement OPTIONAL, 
gmsc-Address [8] ISDN-AddressString OPTIONAL, 
callReferenceNumber [9] CallReferenceNumber OPTIONAL, 
or-Interrogation [10] NULL OPTIONAL, 
extensionContainer [11] ExtensionContainer OPTIONAL, 
...} 

ProvideRoamingNumberRes ::= SEQUENCE { 
roamingNumber ISDN-AddressString, 
extensionContainer ExtensionContainer OPTIONAL, 
...} 


ResumeCallHandlingArg ::= SEQUENCE { 
callReferenceNumber [0] CallReferenceNumber, 
basicServiceGroup [1] Ext-BasicServiceCode, 
forwardingData [2] ForwardingData, 
imsi [3] IMSI, 
cug-CheckInfo [4] CUG-CheckInfo OPTIONAL, 
o-CSI [5] O-CSI OPTIONAL, 
extensionContainer [7] ExtensionContainer OPTIONAL, 
...} 

ResumeCallHandlingRes ::= SEQUENCE { 
extensionContainer ExtensionContainer OPTIONAL, 
...} 

CamelInfo ::= SEQUENCE { 
supportedCamelPhases SupportedCamelPhases, 
suppress-T-CSI NULL OPTIONAL, 
extensionContainer ExtensionContainer OPTIONAL, 
...} 

--change for compiler 
--change for compiler ExtendedRoutingInfo ::= CHOICE { 
--change for compiler routingInfo RoutingInfo, 
--change for compiler camelRoutingInfo [8] CamelRoutingInfo} 
--change for compiler 

----------------------------------------------------------------------
-- Flattened type ExtendedRoutingInfo (no more recursive CHOICE).
----------------------------------------------------------------------

ExtendedRoutingInfo ::= CHOICE {
   roamingNumber ISDN-AddressString,
   forwardingData ForwardingData,  
    camelRoutingInfo    [8] CamelRoutingInfo}


CamelRoutingInfo ::= SEQUENCE { 
forwardingData ForwardingData OPTIONAL, 
gmscCamelSubscriptionInfo [0] GmscCamelSubscriptionInfo, 
extensionContainer [1] ExtensionContainer OPTIONAL, 
...} 

GmscCamelSubscriptionInfo ::= SEQUENCE { 
t-CSI [0] T-CSI OPTIONAL, 
o-CSI [1] O-CSI OPTIONAL, 
extensionContainer [2] ExtensionContainer OPTIONAL, 
...} 

T-CSI ::= SEQUENCE { 
t-BcsmCamelTDPDataList T-BcsmCamelTDPDataList, 
extensionContainer ExtensionContainer OPTIONAL, 
...} 

T-BcsmCamelTDPDataList ::= SEQUENCE SIZE (1..maxNumOfCamelTDPData) OF 
T-BcsmCamelTDPData 

T-BcsmCamelTDPData ::= SEQUENCE { 
t-BcsmTriggerDetectionPoint T-BcsmTriggerDetectionPoint, 
serviceKey ServiceKey, 
gsmSCF-Address [0] ISDN-AddressString, 
defaultCallHandling [1] DefaultCallHandling, 
extensionContainer [2] ExtensionContainer OPTIONAL, 
...} 

T-BcsmTriggerDetectionPoint ::= ENUMERATED { 
termAttemptAuthorized(12), 
...} 
-- exception handling: 
-- For T-BcsmCamelTDPData sequences containing this parameter with any oth204
-- value thanthe ones listed the receiver shall ignore the whole 
-- T-BcsmCamelTDPData sequence. 

--not used 
--not used END 
--not used 

--------------------------------------------------------------------------------
--------------------------------------------------------------------------------
--------------------------------------------------------------------------------


-- Module ----------------------------------------------------------------------
--------------------------------------------------------------------------------
-- MAP SS Data Types.
--------------------------------------------------------------------------------
--------------------------------------------------------------------------------

--not used MAP-SS-DataTypes { 
--not used ccitt identified-organization (4) etsi (0) mobileDomain (0) 
--not used gsm-Network (1) modules (3) map-SS-DataTypes (14) version3 (3)} 
--not used 
--not used DEFINITIONS 
--not used 
--not used IMPLICIT TAGS 
--not used 
--not used ::= 
--not used 
--not used BEGIN 
--not used 
--not used EXPORTS 
--not used RegisterSS-Arg, 
--not used SS-Info, 
--not used SS-Status, 
--not used SS-SubscriptionOption, 
--not used SS-ForBS-Code, 
--not used InterrogateSS-Res, 
--not used USSD-Arg, 
--not used USSD-Res, 
--not used Password, 
--not used GuidanceInfo, 
--not used SS-List, 
--not used SS-InfoList, 
--not used OverrideCategory, 
--not used CliRestrictionOption, 
--not used NoReplyConditionTime, 
--not used ForwardingOptions, 
--not used maxNumOfSS, 
--not used SS-Data, 
--not used USSD-DataCodingScheme, 
--not used USSD-String 
--not used ; 
--not used 
--not used IMPORTS 
--not used AddressString, 
--not used ISDN-AddressString, 
--not used ISDN-SubaddressString, 
--not used BasicServiceCode 
--not used FROM MAP-CommonDataTypes { 
--not used ccitt identified-organization (4) etsi (0) mobileDomain (0) 
--not used gsm-Network (1) modules (3) map-CommonDataTypes (18) version3 (3)} 
--not used 
--not used SS-Code 
--not used FROM MAP-SS-Code { 
--not used ccitt identified-organization (4) etsi (0) mobileDomain (0) 
--not used gsm-Network (1) modules (3) map-SS-Code (15) version3 (3)} 
--not used ; 
--not used 
--not used 

RegisterSS-Arg ::= SEQUENCE{ 
ss-Code SS-Code, 
basicService BasicServiceCode OPTIONAL, 
forwardedToNumber [4] AddressString OPTIONAL, 
forwardedToSubaddress [6] ISDN-SubaddressString OPTIONAL, 
noReplyConditionTime [5] NoReplyConditionTime OPTIONAL, 
...} 

NoReplyConditionTime ::= INTEGER (5..30) 

SS-Info ::= CHOICE { 
forwardingInfo [0] ForwardingInfo, 
callBarringInfo [1] CallBarringInfo, 
ss-Data [3] SS-Data} 

ForwardingInfo ::= SEQUENCE { 
ss-Code SS-Code OPTIONAL, 
forwardingFeatureList ForwardingFeatureList, 
...} 

ForwardingFeatureList ::= 
SEQUENCE SIZE (1..maxNumOfBasicServiceGroups) OF 
ForwardingFeature 

ForwardingFeature ::= SEQUENCE { 
basicService BasicServiceCode OPTIONAL, 
ss-Status [4] SS-Status OPTIONAL, 
forwardedToNumber [5] ISDN-AddressString OPTIONAL, 
forwardedToSubaddress [8] ISDN-SubaddressString OPTIONAL, 
forwardingOptions [6] ForwardingOptions OPTIONAL, 
noReplyConditionTime [7] NoReplyConditionTime OPTIONAL, 
...} 

SS-Status ::= OCTET STRING (SIZE (1)) 

-- bits 8765: 0000 (unused) 
-- bits 4321: Used to convey the "P bit","R bit","A bit" and "Q bit", 
-- representing supplementary service state information 
-- as defined in TS GSM 03.11 

-- bit 4: "Q bit" 

-- bit 3: "P bit" 

-- bit 2: "R bit" 

-- bit 1: "A bit" 

ForwardingOptions ::= OCTET STRING (SIZE (1)) 

-- bit 8: notification to forwarding party 
-- 0 no notification 
-- 1 notification 

-- bit 7: 0 (unused) 

-- bit 6: notification to calling party 
-- 0 no notification 
-- 1 notification 

-- bit 5: 0 (unused) 

-- bits 43: forwarding reason 
-- 00 ms not reachable 
-- 01 ms busy 
-- 10 no reply 
-- 11 unconditional 
-- bits 21: 00 (unused) 

CallBarringInfo ::= SEQUENCE { 
ss-Code SS-Code OPTIONAL, 
callBarringFeatureList CallBarringFeatureList, 
...} 

CallBarringFeatureList ::= 
SEQUENCE SIZE (1..maxNumOfBasicServiceGroups) OF 
CallBarringFeature 

CallBarringFeature ::= SEQUENCE { 
basicService BasicServiceCode OPTIONAL, 
ss-Status [4] SS-Status OPTIONAL, 
...} 

SS-Data ::= SEQUENCE { 
ss-Code SS-Code OPTIONAL, 
ss-Status [4] SS-Status OPTIONAL, 
ss-SubscriptionOption SS-SubscriptionOption OPTIONAL, 
basicServiceGroupList BasicServiceGroupList OPTIONAL, 
...} 

SS-SubscriptionOption ::= CHOICE { 
cliRestrictionOption [2] CliRestrictionOption, 
overrideCategory [1] OverrideCategory} 

CliRestrictionOption ::= ENUMERATED { 
permanent (0), 
temporaryDefaultRestricted (1), 
temporaryDefaultAllowed (2)} 

OverrideCategory ::= ENUMERATED { 
overrideEnabled (0), 
overrideDisabled (1)} 

SS-ForBS-Code ::= SEQUENCE { 
ss-Code SS-Code, 
basicService BasicServiceCode OPTIONAL, 
...} 

Cli-RestrictionInfo ::= SEQUENCE { 
ss-Status SS-Status, 
cliRestrictionOption CliRestrictionOption OPTIONAL, 
...} 

-- Type added for compatibility with MAP V4. Replace type Cli-RestrictionInfo
-- within type InterrogateSS-Res.  
GenericServiceInfo ::= SEQUENCE {
    ss-Status SS-Status,
    cliRestrictionOption CliRestrictionOption OPTIONAL,
    ...}
        
-- Modified type for compatibility with MAP V4. 
InterrogateSS-Res ::= CHOICE { 
ss-Status [0] SS-Status, 
basicServiceGroupList [2] BasicServiceGroupList, 
forwardingFeatureList [3] ForwardingFeatureList, 
-- Used previously before modification.
-- cli-RestrictionInfo [4] Cli-RestrictionInfo}
genericServiceInfo [4] GenericServiceInfo }

USSD-Arg ::= SEQUENCE { 
ussd-DataCodingScheme USSD-DataCodingScheme, 
ussd-String USSD-String, 
...} 

USSD-Res ::= SEQUENCE { 
ussd-DataCodingScheme USSD-DataCodingScheme, 
ussd-String USSD-String, 
...} 

USSD-DataCodingScheme ::= OCTET STRING (SIZE (1)) 
-- The structure of the USSD-DataCodingScheme is defined by 
-- the Cell Broadcast Data Coding Scheme as described in 
-- TS GSM 03.38 

USSD-String ::= OCTET STRING (SIZE (1..maxUSSD-StringLength)) 
-- The structure of the contents of the USSD-String is dependent 
-- on the USSD-DataCodingScheme as described in TS GSM 03.38. 

maxUSSD-StringLength INTEGER ::= 160 

Password ::= NumericString 
(FROM ("0"|"1"|"2"|"3"|"4"|"5"|"6"|"7"|"8"|"9")) 
(SIZE (4)) 

GuidanceInfo ::= ENUMERATED { 
enterPW (0), 
enterNewPW (1), 
enterNewPW-Again (2)} 
-- How this information is really delivered to the subscriber 
-- (display, announcement, ...) is not part of this 
-- specification. 

SS-List ::= SEQUENCE SIZE (1..maxNumOfSS) OF 
SS-Code 

maxNumOfSS INTEGER ::= 30 

SS-InfoList ::= SEQUENCE SIZE (1..maxNumOfSS) OF 
SS-Info 

BasicServiceGroupList ::= SEQUENCE SIZE (1..maxNumOfBasicServiceGroups) OF 
BasicServiceCode 

maxNumOfBasicServiceGroups INTEGER ::= 13 

--not used 
--not used END 
--not used 

--------------------------------------------------------------------------------
--------------------------------------------------------------------------------
--------------------------------------------------------------------------------


-- Module ----------------------------------------------------------------------
--------------------------------------------------------------------------------
-- MAP SS Code.
--------------------------------------------------------------------------------
--------------------------------------------------------------------------------

--not used MAP-SS-Code { 
--not used ccitt identified-organization (4) etsi (0) mobileDomain (0) 
--not used gsm-Network (1) modules (3) map-SS-Code (15) version3 (3)} 
--not used 
--not used DEFINITIONS 
--not used 
--not used ::= 
--not used 
--not used BEGIN 
--not used 
SS-Code ::= OCTET STRING (SIZE (1)) 
-- This type is used to represent the code identifying a single 
-- supplementary service, a group of supplementary services, or 
-- all supplementary services. The services and abbreviations 
-- used are defined in TS GSM 02.04. The internal structure is 
-- defined as follows: 
-- 
-- bits 87654321: group (bits 8765), and specific service 
-- (bits 4321) 

allSS SS-Code ::= '00000000'B 
-- reserved for possible future use 
-- all SS 

allLineIdentificationSS SS-Code ::= '00010000'B 
-- reserved for possible future use 
-- all line identification SS 
clip SS-Code ::= '00010001'B 
-- calling line identification presentation 
clir SS-Code ::= '00010010'B 
-- calling line identification restriction 
colp SS-Code ::= '00010011'B 
-- connected line identification presentation 
colr SS-Code ::= '00010100'B 
-- connected line identification restriction 
mci SS-Code ::= '00010101'B 
-- reserved for possible future use 
-- malicious call identification 


allForwardingSS SS-Code ::= '00100000'B 
-- all forwarding SS 
cfu SS-Code ::= '00100001'B 
-- call forwarding unconditional 
allCondForwardingSS SS-Code ::= '00101000'B 
-- all conditional forwarding SS 
cfb SS-Code ::= '00101001'B 
-- call forwarding on mobile subscriber busy 
cfnry SS-Code ::= '00101010'B 
-- call forwarding on no reply 
cfnrc SS-Code ::= '00101011'B 
-- call forwarding on mobile subscriber not reachable 

allCallOfferingSS SS-Code ::= '00110000'B 
-- reserved for possible future use 
-- all call offering SS includes also all forwarding SS 
ect SS-Code ::= '00110001'B 
-- explicit call transfer 
mah SS-Code ::= '00110010'B 
-- reserved for possible future use 
-- mobile access hunting 

allCallCompletionSS SS-Code ::= '01000000'B 
-- reserved for possible future use 
-- all Call completion SS 
cw SS-Code ::= '01000001'B 
-- call waiting 
hold SS-Code ::= '01000010'B 
-- call hold 
ccbs SS-Code ::= '01000011'B 
-- reserved for possible future use 
-- completion of call to busy subscribers 

allMultiPartySS SS-Code ::= '01010000'B 
-- reserved for possible future use 
-- all multiparty SS 
multiPTY SS-Code ::= '01010001'B 
-- multiparty 

allCommunityOfInterest-SS SS-Code ::= '01100000'B 
-- reserved for possible future use 
-- all community of interest SS 
cug SS-Code ::= '01100001'B 
-- closed user group 

allChargingSS SS-Code ::= '01110000'B 
-- reserved for possible future use 
-- all charging SS 
aoci SS-Code ::= '01110001'B 
-- advice of charge information 
aocc SS-Code ::= '01110010'B 
-- advice of charge charging 

allAdditionalInfoTransferSS SS-Code ::= '10000000'B 
-- reserved for possible future use 
-- all additional information transfer SS 
uus SS-Code ::= '10000001'B 
-- reserved for possible future use 
-- UUS user-to-user signalling 

allBarringSS SS-Code ::= '10010000'B 
-- all barring SS 
barringOfOutgoingCalls SS-Code ::= '10010001'B 
-- barring of outgoing calls 
baoc SS-Code ::= '10010010'B 
-- barring of all outgoing calls 
boic SS-Code ::= '10010011'B 
-- barring of outgoing international calls 
boicExHC SS-Code ::= '10010100'B 
-- barring of outgoing international calls except those directed 
-- to the home PLMN 
barringOfIncomingCalls SS-Code ::= '10011001'B 
-- barring of incoming calls 
baic SS-Code ::= '10011010'B 
-- barring of all incoming calls 
bicRoam SS-Code ::= '10011011'B 
-- barring of incoming calls when roaming outside home PLMN 
-- Country 

allPLMN-specificSS SS-Code ::= '11110000'B 
plmn-specificSS-1 SS-Code ::= '11110001'B 
plmn-specificSS-2 SS-Code ::= '11110010'B 
plmn-specificSS-3 SS-Code ::= '11110011'B 
plmn-specificSS-4 SS-Code ::= '11110100'B 
plmn-specificSS-5 SS-Code ::= '11110101'B 
plmn-specificSS-6 SS-Code ::= '11110110'B 
plmn-specificSS-7 SS-Code ::= '11110111'B 
plmn-specificSS-8 SS-Code ::= '11111000'B 
plmn-specificSS-9 SS-Code ::= '11111001'B 
plmn-specificSS-A SS-Code ::= '11111010'B 
plmn-specificSS-B SS-Code ::= '11111011'B 
plmn-specificSS-C SS-Code ::= '11111100'B 
plmn-specificSS-D SS-Code ::= '11111101'B 
plmn-specificSS-E SS-Code ::= '11111110'B 
plmn-specificSS-F SS-Code ::= '11111111'B 

allCallPrioritySS SS-Code ::= '10100000'B 
-- reserved for possible future use 
-- all call priority SS 
emlpp SS-Code ::= '10100001'B 
-- enhanced Multilevel Precedence Pre-emption (EMLPP) service 

--not used 
--not used END 
--not used 

--------------------------------------------------------------------------------
--------------------------------------------------------------------------------
--------------------------------------------------------------------------------


-- Module ----------------------------------------------------------------------
--------------------------------------------------------------------------------
-- MAP SM Data Types.
--------------------------------------------------------------------------------
--------------------------------------------------------------------------------

--not used MAP-SM-DataTypes { 
--not used ccitt identified-organization (4) etsi (0) mobileDomain (0) 
--not used gsm-Network (1) modules (3) map-SM-DataTypes (16) version3 (3)} 
--not used 
--not used DEFINITIONS 
--not used 
--not used IMPLICIT TAGS 
--not used 
--not used ::= 
--not used 
--not used BEGIN 
--not used 
--not used EXPORTS 
--not used RoutingInfoForSM-Arg, 
--not used RoutingInfoForSM-Res, 
--not used MO-ForwardSM-Arg, 
--not used MO-ForwardSM-Res, 
--not used MT-ForwardSM-Arg, 
--not used MT-ForwardSM-Res, 
--not used ReportSM-DeliveryStatusArg, 
--not used ReportSM-DeliveryStatusRes, 
--not used AlertServiceCentreArg, 
--not used InformServiceCentreArg, 
--not used ReadyForSM-Arg, 
--not used SM-DeliveryOutcome, 
--not used AlertReason 
--not used ; 
--not used 
--not used IMPORTS 
--not used AddressString, 
--not used ISDN-AddressString, 
--not used SignalInfo, 
--not used IMSI, 
--not used LMSI 
--not used FROM MAP-CommonDataTypes { 
--not used ccitt identified-organization (4) etsi (0) mobileDomain (0) 
--not used gsm-Network (1) modules (3) map-CommonDataTypes (18) version3 (3)} 
--not used 
--not used AbsentSubscriberDiagnosticSM 
--not used FROM MAP-ER-DataTypes { 
--not used ccitt identified-organization (4) etsi (0) mobileDomain (0) 
--not used gsm-Network (1) modules (3) map-ER-DataTypes (17) version3 (3)} 
--not used 
--not used ExtensionContainer 
--not used FROM MAP-ExtensionDataTypes { 
--not used ccitt identified-organization (4) etsi (0) mobileDomain (0) 
--not used gsm-Network (1) modules (3) map-ExtensionDataTypes (21) version3 (3)} 
--not used ; 
--not used 
--not used 


RoutingInfoForSM-Arg ::= SEQUENCE { 
msisdn [0] ISDN-AddressString, 
sm-RP-PRI [1] BOOLEAN, 
serviceCentreAddress [2] AddressString, 
extensionContainer [6] ExtensionContainer OPTIONAL, 
...} 

RoutingInfoForSM-Res::= SEQUENCE { 
imsi IMSI, 
locationInfoWithLMSI [0] LocationInfoWithLMSI, 
extensionContainer [4] ExtensionContainer OPTIONAL, 
...} 

LocationInfoWithLMSI ::= SEQUENCE { 
-- Used previously before modification.
-- msc-Number [1] ISDN-AddressString, 
networkNode-Number [1] ISDN-AddressString,
lmsi LMSI OPTIONAL, 
extensionContainer ExtensionContainer OPTIONAL, 
...} 

MO-ForwardSM-Arg ::= SEQUENCE { 
sm-RP-DA SM-RP-DA, 
sm-RP-OA SM-RP-OA, 
sm-RP-UI SignalInfo, 
extensionContainer ExtensionContainer OPTIONAL, 
...} 

MO-ForwardSM-Res ::= SEQUENCE { 
sm-RP-UI SignalInfo OPTIONAL, 
extensionContainer ExtensionContainer OPTIONAL, 
...} 

MT-ForwardSM-Arg ::= SEQUENCE { 
sm-RP-DA SM-RP-DA, 
sm-RP-OA SM-RP-OA, 
sm-RP-UI SignalInfo, 
moreMessagesToSend NULL OPTIONAL, 
extensionContainer ExtensionContainer OPTIONAL, 
...} 

MT-ForwardSM-Res ::= SEQUENCE { 
sm-RP-UI SignalInfo OPTIONAL, 
extensionContainer ExtensionContainer OPTIONAL, 
...} 

SM-RP-DA ::= CHOICE { 
imsi [0] IMSI, 
lmsi [1] LMSI, 
serviceCentreAddressDA [4] AddressString, 
noSM-RP-DA [5] NULL} 

SM-RP-OA ::= CHOICE { 
msisdn [2] ISDN-AddressString, 
serviceCentreAddressOA [4] AddressString, 
noSM-RP-OA [5] NULL} 

ReportSM-DeliveryStatusArg ::= SEQUENCE { 
msisdn ISDN-AddressString, 
serviceCentreAddress AddressString, 
sm-DeliveryOutcome SM-DeliveryOutcome, 
absentSubscriberDiagnosticSM [0] AbsentSubscriberDiagnosticSM 
OPTIONAL, 
extensionContainer [1] ExtensionContainer OPTIONAL, 
...} 

SM-DeliveryOutcome ::= ENUMERATED { 
memoryCapacityExceeded (0), 
absentSubscriber (1), 
successfulTransfer (2)} 

ReportSM-DeliveryStatusRes ::= SEQUENCE { 
storedMSISDN ISDN-AddressString OPTIONAL, 
extensionContainer ExtensionContainer OPTIONAL, 
...} 

AlertServiceCentreArg ::= SEQUENCE { 
msisdn ISDN-AddressString, 
serviceCentreAddress AddressString, 
...} 

InformServiceCentreArg ::= SEQUENCE { 
storedMSISDN ISDN-AddressString OPTIONAL, 
mw-Status MW-Status OPTIONAL, 
extensionContainer ExtensionContainer OPTIONAL, 
...} 

MW-Status ::= BIT STRING { 
sc-AddressNotIncluded (0), 
mnrf-Set (1), 
mcef-Set (2),
mnrg-Set (3)} (SIZE (6..16)) 
-- exception handling: 
-- bits 3 to 15 shall be ignored if received and not understood 

ReadyForSM-Arg ::= SEQUENCE { 
imsi [0] IMSI, 
alertReason AlertReason, 
...} 

AlertReason ::= ENUMERATED { 
ms-Present (0), 
memoryAvailable (1)} 

--not used 
--not used END 
--not used 

--------------------------------------------------------------------------------
--------------------------------------------------------------------------------
--------------------------------------------------------------------------------


-- Module ----------------------------------------------------------------------
--------------------------------------------------------------------------------
-- MAP ER Data Types.
--------------------------------------------------------------------------------
--------------------------------------------------------------------------------

--not used MAP-ER-DataTypes { 
--not used ccitt identified-organization (4) etsi (0) mobileDomain (0) 
--not used gsm-Network (1) modules (3) map-ER-DataTypes (17) version3 (3)} 
--not used 
--not used DEFINITIONS 
--not used 
--not used IMPLICIT TAGS 
--not used 
--not used ::= 
--not used 
--not used BEGIN 
--not used 
--not used EXPORTS 
--not used RoamingNotAllowedParam, 
--not used CallBarredParam, 
--not used CUG-RejectParam, 
--not used SS-IncompatibilityCause, 
--not used PW-RegistrationFailureCause, 
--not used SM-DeliveryFailureCause, 
--not used SystemFailureParam, 
--not used DataMissingParam, 
--not used UnexpectedDataParam, 
--not used FacilityNotSupParam, 
--not used OR-NotAllowedParam, 
--not used UnknownSubscriberParam, 
--not used NumberChangedParam, 
--not used UnidentifiedSubParam, 
--not used IllegalSubscriberParam, 
--not used IllegalEquipmentParam, 
--not used BearerServNotProvParam, 
--not used TeleservNotProvParam, 
--not used TracingBufferFullParam, 
--not used NoRoamingNbParam, 
--not used AbsentSubscriberParam, 
--not used BusySubscriberParam, 
--not used NoSubscriberReplyParam, 
--not used ForwardingViolationParam, 
--not used ForwardingFailedParam, 
--not used ATI-NotAllowedParam, 
--not used SubBusyForMT-SMS-Param, 
--not used MessageWaitListFullParam, 
--not used AbsentSubscriberSM-Param, 
--not used AbsentSubscriberDiagnosticSM 
--not used 
--not used ; 
--not used 
--not used IMPORTS 
--not used SS-Status 
--not used FROM MAP-SS-DataTypes { 
--not used ccitt identified-organization (4) etsi (0) mobileDomain (0) 
--not used gsm-Network (1) modules (3) map-SS-DataTypes (14) version3 (3)} 
--not used 
--not used SignalInfo, 
--not used BasicServiceCode, 
--not used NetworkResource 
--not used FROM MAP-CommonDataTypes { 
--not used ccitt identified-organization (4) etsi (0) mobileDomain (0) 
--not used gsm-Network (1) modules (3) map-CommonDataTypes (18) version3 (3)} 
--not used 
--not used SS-Code 
--not used FROM MAP-SS-Code { 
--not used ccitt identified-organization (4) etsi (0) mobileDomain (0) 
--not used gsm-Network (1) modules (3) map-SS-Code (15) version3 (3)} 
--not used 
--not used ExtensionContainer 
--not used FROM MAP-ExtensionDataTypes { 
--not used ccitt identified-organization (4) etsi (0) mobileDomain (0) 
--not used gsm-Network (1) modules (3) map-ExtensionDataTypes (21) version3 (3)} 
--not used ; 
--not used 

RoamingNotAllowedParam ::= SEQUENCE { 
roamingNotAllowedCause RoamingNotAllowedCause, 
extensionContainer ExtensionContainer OPTIONAL, 
...} 


RoamingNotAllowedCause ::= ENUMERATED { 
plmnRoamingNotAllowed (0), 
operatorDeterminedBarring (3)} 

CallBarredParam ::= CHOICE { 
callBarringCause CallBarringCause, 
-- call BarringCause must not be used in version 3 
extensibleCallBarredParam ExtensibleCallBarredParam 
-- extensibleCallBarredParam must not be used in version <3 
} 

CallBarringCause ::= ENUMERATED { 
barringServiceActive (0), 
operatorBarring (1)} 

ExtensibleCallBarredParam ::= SEQUENCE { 
callBarringCause CallBarringCause OPTIONAL, 
extensionContainer ExtensionContainer OPTIONAL, 
...} 

CUG-RejectParam ::= SEQUENCE { 
cug-RejectCause CUG-RejectCause OPTIONAL, 
extensionContainer ExtensionContainer OPTIONAL, 
...} 

CUG-RejectCause ::= ENUMERATED { 
incomingCallsBarredWithinCUG (0), 
subscriberNotMemberOfCUG (1), 
requestedBasicServiceViolatesCUG-Constraints (5), 
calledPartySS-InteractionViolation (7)} 

SS-IncompatibilityCause ::= SEQUENCE { 
ss-Code [1] SS-Code OPTIONAL, 
basicService BasicServiceCode OPTIONAL, 
ss-Status [4] SS-Status OPTIONAL, 
...} 

PW-RegistrationFailureCause ::= ENUMERATED { 
undetermined (0), 
invalidFormat (1), 
newPasswordsMismatch (2)} 


SM-EnumeratedDeliveryFailureCause ::= ENUMERATED { 
memoryCapacityExceeded (0), 
equipmentProtocolError (1), 
equipmentNotSM-Equipped (2), 
unknownServiceCentre (3), 
sc-Congestion (4), 
invalidSME-Address (5), 
subscriberNotSC-Subscriber (6)} 

SM-DeliveryFailureCause ::= SEQUENCE { 
sm-EnumeratedDeliveryFailureCause 
SM-EnumeratedDeliveryFailureCause, 
diagnosticInfo SignalInfo OPTIONAL, 
extensionContainer ExtensionContainer OPTIONAL, 
...} 

AbsentSubscriberSM-Param ::= SEQUENCE { 
absentSubscriberDiagnosticSM AbsentSubscriberDiagnosticSM OPTIONAL, 
extensionContainer ExtensionContainer OPTIONAL, 
...} 

AbsentSubscriberDiagnosticSM ::= INTEGER (0..255) 
-- AbsentSubscriberDiagnosticSM values are defined in ETS 300 536 (GSM 03.4141

SystemFailureParam ::= CHOICE { 
networkResource NetworkResource, 
-- networkResource must not be used in version 3 
extensibleSystemFailureParam ExtensibleSystemFailureParam 
-- extensibleSystemFailureParam must not be used in version <3 
} 

ExtensibleSystemFailureParam ::= SEQUENCE { 
networkResource NetworkResource OPTIONAL, 
extensionContainer ExtensionContainer OPTIONAL, 
...} 

DataMissingParam ::= SEQUENCE { 
extensionContainer ExtensionContainer OPTIONAL, 
...} 

UnexpectedDataParam ::= SEQUENCE { 
extensionContainer ExtensionContainer OPTIONAL, 
...} 

FacilityNotSupParam ::= SEQUENCE { 
extensionContainer ExtensionContainer OPTIONAL, 
...} 

OR-NotAllowedParam ::= SEQUENCE { 
extensionContainer ExtensionContainer OPTIONAL, 
...} 

UnknownSubscriberParam ::= SEQUENCE { 
extensionContainer ExtensionContainer OPTIONAL, 
...} 

NumberChangedParam ::= SEQUENCE { 
extensionContainer ExtensionContainer OPTIONAL, 
...} 

UnidentifiedSubParam ::= SEQUENCE { 
extensionContainer ExtensionContainer OPTIONAL, 
...} 

IllegalSubscriberParam ::= SEQUENCE { 
extensionContainer ExtensionContainer OPTIONAL, 
...} 

IllegalEquipmentParam ::= SEQUENCE { 
extensionContainer ExtensionContainer OPTIONAL, 
...} 

BearerServNotProvParam ::= SEQUENCE { 
extensionContainer ExtensionContainer OPTIONAL, 
...} 

TeleservNotProvParam ::= SEQUENCE { 
extensionContainer ExtensionContainer OPTIONAL, 
...} 

TracingBufferFullParam ::= SEQUENCE { 
extensionContainer ExtensionContainer OPTIONAL, 
...} 

NoRoamingNbParam ::= SEQUENCE { 
extensionContainer ExtensionContainer OPTIONAL, 
...} 

AbsentSubscriberParam ::= SEQUENCE { 
extensionContainer ExtensionContainer OPTIONAL, 
...} 

BusySubscriberParam ::= SEQUENCE { 
extensionContainer ExtensionContainer OPTIONAL, 
...} 

NoSubscriberReplyParam ::= SEQUENCE { 
extensionContainer ExtensionContainer OPTIONAL, 
...} 

ForwardingViolationParam ::= SEQUENCE { 
extensionContainer ExtensionContainer OPTIONAL, 
...} 

ForwardingFailedParam ::= SEQUENCE { 
extensionContainer ExtensionContainer OPTIONAL, 
...} 
ATI-NotAllowedParam ::= SEQUENCE { 
extensionContainer ExtensionContainer OPTIONAL, 
...} 

SubBusyForMT-SMS-Param ::= SEQUENCE { 
extensionContainer ExtensionContainer OPTIONAL, 
...} 

MessageWaitListFullParam ::= SEQUENCE { 
extensionContainer ExtensionContainer OPTIONAL, 
...} 

--not used 
--not used END 
--not used 

--------------------------------------------------------------------------------
--------------------------------------------------------------------------------
--------------------------------------------------------------------------------


-- Module ----------------------------------------------------------------------
--------------------------------------------------------------------------------
-- MAP Common Data Types.
--------------------------------------------------------------------------------
--------------------------------------------------------------------------------

--not used MAP-CommonDataTypes { 
--not used ccitt identified-organization (4) etsi (0) mobileDomain (0) 
--not used gsm-Network (1) modules (3) map-CommonDataTypes (18) version3 (3)} 
--not used 
--not used DEFINITIONS 
--not used 
--not used IMPLICIT TAGS 
--not used 
--not used ::= 
--not used 
--not used BEGIN 
--not used 
--not used EXPORTS 
--not used 
-- general data types and values 
--not used AddressString, 
--not used ISDN-AddressString, 
--not used ISDN-SubaddressString, 
--not used ExternalSignalInfo, 
--not used SignalInfo, 
--not used maxSignalInfoLength, 
--not used 
-- data types for numbering and identification 
--not used IMSI, 
--not used TMSI, 
--not used SubscriberId, 
--not used IMEI, 
--not used HLR-List, 
--not used LMSI, 
--not used GlobalCellId, 
--not used NetworkResource, 
--not used 
-- data types for CAMEL 
--not used CellIdOrLAI, 
--not used 
-- data types for subscriber management 
--not used BasicServiceCode, 
--not used Ext-BasicServiceCode 
--not used ; 
--not used 
--not used IMPORTS 
--not used TeleserviceCode, 
--not used Ext-TeleserviceCode 
--not used FROM MAP-TS-Code { 
--not used ccitt identified-organization (4) etsi (0) mobileDomain (0) 
--not used gsm-Network (1) modules (3) map-TS-Code (19) version3 (3)} 
--not used 
--not used BearerServiceCode, 
--not used Ext-BearerServiceCode 
--not used FROM MAP-BS-Code { 
--not used ccitt identified-organization (4) etsi (0) mobileDomain (0) 
--not used gsm-Network (1) modules (3) map-BS-Code (20) version3 (3)} 
--not used 
--not used ExtensionContainer 
--not used FROM MAP-ExtensionDataTypes { 
--not used ccitt identified-organization (4) etsi (0) mobileDomain (0) 
--not used gsm-Network (1) modules (3) map-ExtensionDataTypes (21) version3 (3)} 
--not used ; 
--not used 
--not used 
-- general data types 
--not used 

TBCD-STRING ::= OCTET STRING 
-- This type (Telephony Binary Coded Decimal String) is used to 
-- represent several digits from 0 through 9, *, #, a, b, c, two 
-- digits per octet, each digit encoded 0000 to 1001 (0 to 9), 
-- 1010 (*), 1011 (#), 1100 (a), 1101 (b) or 1110 (c); 1111 used 
-- as filler when there is an odd number of digits. 

-- bits 8765 of octet n encoding digit 2n 
-- bits 4321 of octet n encoding digit 2(n-1) +1 


AddressString ::= OCTET STRING (SIZE (1..maxAddressLength)) 
-- This type is used to represent a number for addressing 
-- purposes. It is composed of 
-- a) one octet for nature of address, and numbering plan 
-- indicator. 
-- b) digits of an address encoded as TBCD-String. 

-- a) The first octet includes a one bit extension indicator, a 
-- 3 bits nature of address indicator and a 4 bits numbering 
-- plan indicator, encoded as follows: 

-- bit 8: 1 (no extension) 

-- bits 765: nature of address indicator 
-- 000 unknown 
-- 001 international number 
-- 010 national significant number 
-- 011 network specific number 
-- 100 subscriber number 
-- 101 reserved 
-- 110 abbreviated number 
-- 111 reserved for extension 

-- bits 4321: numbering plan indicator 
-- 0000 unknown 
-- 0001 ISDN/Telephony Numbering Plan (Rec CCITT E.164) 
-- 0010 spare 
-- 0011 data numbering plan (CCITT Rec X.121) 
-- 0100 telex numbering plan (CCITT Rec F.69) 
-- 0101 spare 
-- 0110 land mobile numbering plan (CCITT Rec E.212) 
-- 0111 spare 
-- 1000 national numbering plan 
-- 1001 private numbering plan 
-- 1111 reserved for extension 

-- all other values are reserved. 

-- b) The following octets representing digits of an address 
-- encoded as a TBCD-STRING. 

maxAddressLength INTEGER ::= 20 

ISDN-AddressString ::= 
AddressString (SIZE (1..maxISDN-AddressLength)) 
-- This type is used to represent ISDN numbers. 

--change for compiler (common type with MAP V1) maxISDN-AddressLength  INTEGER ::= 9
maxISDN-AddressLength INTEGER ::= 10 

ISDN-SubaddressString ::= 
OCTET STRING (SIZE (1..maxISDN-SubaddressLength)) 
-- This type is used to represent ISDN subaddresses. 
-- It is composed of 
-- a) one octet for type of subaddress and odd/even indicator. 
-- b) 20 octets for subaddress information. 

-- a) The first octet includes a one bit extension indicator, a 
-- 3 bits type of subaddress and a one bit odd/even indicator, 
-- encoded as follows: 

-- bit 8: 1 (no extension) 

-- bits 765: type of subaddress 
-- 000 NSAP (X.213/ISO 8348 AD2) 
-- 010 User Specified 
-- All other values are reserved 

-- bit 4: odd/even indicator 
-- 0 even number of address signals 
-- 1 odd number of address signals 
-- The odd/even indicator is used when the type of subaddress 
-- is "user specified" and the coding is BCD. 

-- bits 321: 000 (unused) 

-- b) Subaddress information. 
-- The NSAP X.213/ISO8348AD2 address shall be formatted as specified 
-- by octet 4 which contains the Authority and Format Identifier 
-- (AFI). The encoding is made according to the "preferred binary 
-- encoding" as defined in X.213/ISO834AD2. For the definition 
-- of this type of subaddress, see CCITT Rec I.334. 

-- For User-specific subaddress, this field is encoded according 
-- to the user specification, subject to a maximum length of 20 
-- octets. When interworking with X.25 networks BCD coding should 
-- be applied. 

maxISDN-SubaddressLength INTEGER ::= 21 

ExternalSignalInfo ::= SEQUENCE { 
protocolId ProtocolId, 
signalInfo SignalInfo, 
-- Information about the internal structure is given in 
-- subclause 5.6.9. 
extensionContainer ExtensionContainer OPTIONAL, 
-- extensionContainer must not be used in version 2 
...} 

SignalInfo ::= OCTET STRING (SIZE (1..maxSignalInfoLength)) 

maxSignalInfoLength INTEGER ::= 200 
-- This NamedValue represents the theoretical maximum number of 
-- octets which are available to carry a single data type, 
-- without requiring segmentation to cope with the network layer 
-- service. However, the actual maximum size available for a data 
-- type may be lower, especially when other information elements 
-- have to be included in the same component. 

ProtocolId ::= ENUMERATED { 
gsm-0408 (1), 
gsm-0806 (2), 
gsm-BSSMAP (3), 
-- Value 3 is reserved and must not be used 
ets-300102-1 (4)} 


-- data types for numbering and identification 

--change for compiler (common type with MAP V1) IMSI ::= TBCD-STRING (SIZE (3..8))
IMSI ::= TBCD-STRING (SIZE (2..8)) 
-- digits of MCC, MNC, MSIN are concatenated in this order. 

TMSI ::= OCTET STRING (SIZE (1..4)) 

SubscriberId ::= CHOICE { 
imsi [0] IMSI, 
tmsi [1] TMSI} 

IMEI ::= TBCD-STRING (SIZE (8)) 
-- Refers to International Mobile Station Equipment Identity 
-- and Software Version Number (SVN) defined in TS GSM 03.03. 
-- If the SVN is not present the last octet shall contain the 
-- digit 0 and a filler. 
-- If present the SVN shall be included in the last octet. 

HLR-Id ::= IMSI 
-- leading digits of IMSI, i.e. (MCC, MNC, leading digits of 
-- MSIN) forming HLR Id defined in TS GSM 03.03. 

HLR-List ::= SEQUENCE SIZE (1..maxNumOfHLR-Id) OF 
HLR-Id 

maxNumOfHLR-Id INTEGER ::= 50 

LMSI ::= OCTET STRING (SIZE (4)) 

GlobalCellId ::= OCTET STRING (SIZE (5..7)) 
-- Refers to Cell Global Identification defined in TS GSM 03.03. 
-- Octets are coded according to TS GSM 04.08. 
-- The internal structure is defined as follows: 
-- Mobile Country Code: 3 digits according to CCITT Rec E.212 
-- 1 digit filler (1111) 
-- Mobile Network Code: 2 digits according to CCITT Rec E.212 
-- Location Area Code: 2 octets according to TS GSM 04.08 
-- Cell Identity: 2 octets (CI) according to TS GSM 04.08 

NetworkResource ::= ENUMERATED { 
plmn (0), 
hlr (1), 
vlr (2), 
pvlr (3), 
controllingMSC (4), 
vmsc (5), 
eir (6), 
rss (7)} 

-- data types for CAMEL 

CellIdOrLAI ::= CHOICE { 
cellIdFixedLength [0] CellIdFixedLength, 
laiFixedLength [1] LAIFixedLength} 

CellIdFixedLength ::= OCTET STRING (SIZE (7)) 
-- Refers to Cell Global Identification defined in TS GSM 03.03. 
-- Octets are coded according to TS GSM 04.08. 
-- The internal structure is defined as follows: 
-- Mobile Country Code: 3 digits according to CCITT Rec E.212 
-- 1 digit filler (1111) 
-- Mobile Network Code: 2 digits according to CCITT Rec E.212 
-- Location Area Code: 2 octets according to TS GSM 04.08 
-- Cell Identity: 2 octets (CI) according to TS GSM 04.08 

LAIFixedLength ::= OCTET STRING (SIZE (5)) 
-- Refers to Location Area Identification defined in TS GSM 03.03. 
-- Octets are coded according to TS GSM 04.08. 
-- The internal structure is defined as follows: 
-- Mobile Country Code: 3 digits according to CCITT Rec E.212 
-- 1 digit filler (1111) 
-- Mobile Network Code: 2 digits according to CCITT Rec E.212 
-- Location Area Code: 2 octets according to TS GSM 04.08 

-- data types for subscriber management 

BasicServiceCode ::= CHOICE { 
bearerService [2] BearerServiceCode, 
teleservice [3] TeleserviceCode} 

Ext-BasicServiceCode ::= CHOICE { 
ext-BearerService [2] Ext-BearerServiceCode, 
ext-Teleservice [3] Ext-TeleserviceCode} 

--not used 
--not used END 
--not used 

--------------------------------------------------------------------------------
--------------------------------------------------------------------------------
--------------------------------------------------------------------------------


-- Module ----------------------------------------------------------------------
--------------------------------------------------------------------------------
-- MAP TS Code.
--------------------------------------------------------------------------------
--------------------------------------------------------------------------------

--not used MAP-TS-Code { 
--not used ccitt identified-organization (4) etsi (0) mobileDomain (0) 
--not used gsm-Network (1) modules (3) map-TS-Code (19) version3 (3)} 
--not used 
--not used DEFINITIONS 
--not used 
--not used ::= 
--not used 
--not used BEGIN 
--not used 
TeleserviceCode ::= OCTET STRING (SIZE (1)) 
-- This type is used to represent the code identifying a single 
-- teleservice, a group of teleservices, or all teleservices. The 
-- services are defined in TS GSM 02.03. 
-- The internal structure is defined as follows: 

-- bits 87654321: group (bits 8765) and specific service 
-- (bits 4321) 

Ext-TeleserviceCode ::= OCTET STRING (SIZE (1..5)) 
-- This type is used to represent the code identifying a single 
-- teleservice, a group of teleservices, or all teleservices. The 
-- services are defined in TS GSM 02.03. 
-- The internal structure is defined as follows: 

-- OCTET 1: 
-- bits 87654321: group (bits 8765) and specific service 
-- (bits 4321) 

-- OCTETS 2-5: reserved for future use. If received the 
-- Ext-TeleserviceCode shall be 
-- treated according to the exception handling defined for the 
-- operation that uses this type. 

-- Ext-TeleserviceCode includes all values defined for TeleserviceCode. 


allTeleservices TeleserviceCode ::= '00000000'B 

allSpeechTransmissionServices TeleserviceCode ::= '00010000'B 
telephony TeleserviceCode ::= '00010001'B 
emergencyCalls TeleserviceCode ::= '00010010'B 

allShortMessageServices TeleserviceCode ::= '00100000'B 
shortMessageMT-PP TeleserviceCode ::= '00100001'B 
shortMessageMO-PP TeleserviceCode ::= '00100010'B 

allFacsimileTransmissionServices TeleserviceCode ::= '01100000'B 
facsimileGroup3AndAlterSpeech TeleserviceCode ::= '01100001'B 
automaticFacsimileGroup3 TeleserviceCode ::= '01100010'B 
facsimileGroup4 TeleserviceCode ::= '01100011'B 

-- The following non-hierarchical Compound Teleservice Groups 
-- are defined in TS GSM 02.30: 
allDataTeleservices TeleserviceCode ::= '01110000'B 
-- covers Teleservice Groups 'allFacsimileTransmissionServices' 
-- and 'allShortMessageServices' 
allTeleservices-ExeptSMS TeleserviceCode ::= '10000000'B 
-- covers Teleservice Groups 'allSpeechTransmissionServices' and 
-- 'allFacsimileTransmissionServices' 
-- 
-- Compound Teleservice Group Codes are only used in call 
-- independent supplementary service operations, i.e. they 
-- are not used in InsertSubscriberData or in 
-- DeleteSubscriberData messages. 

allVoiceGroupCallServices TeleserviceCode ::= '10010000'B 

voiceGroupCall TeleserviceCode ::= '10010001'B 
voiceBroadcastCall TeleserviceCode ::= '10010010'B 

allPLMN-specificTS TeleserviceCode ::= '11010000'B 
plmn-specificTS-1 TeleserviceCode ::= '11010001'B 
plmn-specificTS-2 TeleserviceCode ::= '11010010'B 
plmn-specificTS-3 TeleserviceCode ::= '11010011'B 
plmn-specificTS-4 TeleserviceCode ::= '11010100'B 
plmn-specificTS-5 TeleserviceCode ::= '11010101'B 
plmn-specificTS-6 TeleserviceCode ::= '11010110'B 
plmn-specificTS-7 TeleserviceCode ::= '11010111'B 
plmn-specificTS-8 TeleserviceCode ::= '11011000'B 
plmn-specificTS-9 TeleserviceCode ::= '11011001'B 
plmn-specificTS-A TeleserviceCode ::= '11011010'B 
plmn-specificTS-B TeleserviceCode ::= '11011011'B 
plmn-specificTS-C TeleserviceCode ::= '11011100'B 
plmn-specificTS-D TeleserviceCode ::= '11011101'B 
plmn-specificTS-E TeleserviceCode ::= '11011110'B 
plmn-specificTS-F TeleserviceCode ::= '11011111'B 

--not used 
--not used END 
--not used 

--------------------------------------------------------------------------------
--------------------------------------------------------------------------------
--------------------------------------------------------------------------------


-- Module ----------------------------------------------------------------------
--------------------------------------------------------------------------------
-- MAP BS Code.
--------------------------------------------------------------------------------
--------------------------------------------------------------------------------

--not used MAP-BS-Code { 
--not used ccitt identified-organization (4) etsi (0) mobileDomain (0) 
--not used gsm-Network (1) modules (3) map-BS-Code (20) version3 (3)} 
--not used 
--not used DEFINITIONS 
--not used 
--not used ::= 
--not used 
--not used BEGIN 
--not used 

BearerServiceCode ::= OCTET STRING (SIZE (1)) 
-- This type is used to represent the code identifying a single 
-- bearer service, a group of bearer services, or all bearer 
-- services. The services are defined in TS GSM 02.02. 
-- The internal structure is defined as follows: 
-- 
-- plmn-specific bearer services: 
-- bits 87654321: defined by the HPLMN operator 

-- rest of bearer services: 
-- bit 8: 0 (unused) 
-- bits 7654321: group (bits 7654), and rate, if applicable 
-- (bits 321) 

Ext-BearerServiceCode ::= OCTET STRING (SIZE (1..5)) 
-- This type is used to represent the code identifying a single 
-- bearer service, a group of bearer services, or all bearer 
-- services. The services are defined in TS GSM 02.02. 
-- The internal structure is defined as follows: 
-- 
-- OCTET 1: 
-- plmn-specific bearer services: 
-- bits 87654321: defined by the HPLMN operator 
-- 
-- rest of bearer services: 
-- bit 8: 0 (unused) 
-- bits 7654321: group (bits 7654), and rate, if applicable 
-- (bits 321) 

-- OCTETS 2-5: reserved for future use. If received the 
-- Ext-TeleserviceCode shall be 
-- treated according to the exception handling defined for the 
-- operation that uses this type. 


-- Ext-BearerServiceCode includes all values defined for BearerServiceCode. 


allBearerServices BearerServiceCode ::= '00000000'B 

allDataCDA-Services BearerServiceCode ::= '00010000'B 
dataCDA-300bps BearerServiceCode ::= '00010001'B 
dataCDA-1200bps BearerServiceCode ::= '00010010'B 
dataCDA-1200-75bps BearerServiceCode ::= '00010011'B 
dataCDA-2400bps BearerServiceCode ::= '00010100'B 
dataCDA-4800bps BearerServiceCode ::= '00010101'B 
dataCDA-9600bps BearerServiceCode ::= '00010110'B 
general-dataCDA BearerServiceCode ::= '00010111'B 

allDataCDS-Services BearerServiceCode ::= '00011000'B 
dataCDS-1200bps BearerServiceCode ::= '00011010'B 
dataCDS-2400bps BearerServiceCode ::= '00011100'B 
dataCDS-4800bps BearerServiceCode ::= '00011101'B 
dataCDS-9600bps BearerServiceCode ::= '00011110'B 
general-dataCDS BearerServiceCode ::= '00011111'B 

allPadAccessCA-Services BearerServiceCode ::= '00100000'B 
padAccessCA-300bps BearerServiceCode ::= '00100001'B 
padAccessCA-1200bps BearerServiceCode ::= '00100010'B 
padAccessCA-1200-75bps BearerServiceCode ::= '00100011'B 
padAccessCA-2400bps BearerServiceCode ::= '00100100'B 
padAccessCA-4800bps BearerServiceCode ::= '00100101'B 
padAccessCA-9600bps BearerServiceCode ::= '00100110'B 
general-padAccessCA BearerServiceCode ::= '00100111'B 
allDataPDS-Services BearerServiceCode ::= '00101000'B 
dataPDS-2400bps BearerServiceCode ::= '00101100'B 
dataPDS-4800bps BearerServiceCode ::= '00101101'B 
dataPDS-9600bps BearerServiceCode ::= '00101110'B 
general-dataPDS BearerServiceCode ::= '00101111'B 

allAlternateSpeech-DataCDA BearerServiceCode ::= '00110000'B 

allAlternateSpeech-DataCDS BearerServiceCode ::= '00111000'B 

allSpeechFollowedByDataCDA BearerServiceCode ::= '01000000'B 

allSpeechFollowedByDataCDS BearerServiceCode ::= '01001000'B 

-- The following non-hierarchical Compound Bearer Service 
-- Groups are defined in TS GSM 02.30: 
allDataCircuitAsynchronous BearerServiceCode ::= '01010000'B 
-- covers "allDataCDA-Services", "allAlternateSpeech-DataCDA" and 
-- "allSpeechFollowedByDataCDA" 
allAsynchronousServices BearerServiceCode ::= '01100000'B 
-- covers "allDataCDA-Services", "allAlternateSpeech-DataCDA", 
-- "allSpeechFollowedByDataCDA" and "allPadAccessCDA-Services" 
allDataCircuitSynchronous BearerServiceCode ::= '01011000'B 
-- covers "allDataCDS-Services", "allAlternateSpeech-DataCDS" and 
-- "allSpeechFollowedByDataCDS" 
allSynchronousServices BearerServiceCode ::= '01101000'B 
-- covers "allDataCDS-Services", "allAlternateSpeech-DataCDS", 
-- "allSpeechFollowedByDataCDS" and "allDataPDS-Services" 
-- 
-- Compound Bearer Service Group Codes are only used in call 
-- independent supplementary service operations, i.e. they 
-- are not used in InsertSubscriberData or in 
-- DeleteSubscriberData messages. 

allPLMN-specificBS BearerServiceCode ::= '11010000'B 
plmn-specificBS-1 BearerServiceCode ::= '11010001'B 
plmn-specificBS-2 BearerServiceCode ::= '11010010'B 
plmn-specificBS-3 BearerServiceCode ::= '11010011'B 
plmn-specificBS-4 BearerServiceCode ::= '11010100'B 
plmn-specificBS-5 BearerServiceCode ::= '11010101'B 
plmn-specificBS-6 BearerServiceCode ::= '11010110'B 
plmn-specificBS-7 BearerServiceCode ::= '11010111'B 
plmn-specificBS-8 BearerServiceCode ::= '11011000'B 
plmn-specificBS-9 BearerServiceCode ::= '11011001'B 
plmn-specificBS-A BearerServiceCode ::= '11011010'B 
plmn-specificBS-B BearerServiceCode ::= '11011011'B 
plmn-specificBS-C BearerServiceCode ::= '11011100'B 
plmn-specificBS-D BearerServiceCode ::= '11011101'B 
plmn-specificBS-E BearerServiceCode ::= '11011110'B 
plmn-specificBS-F BearerServiceCode ::= '11011111'B 

--not used 
--not used END 
--not used 

--------------------------------------------------------------------------------
--------------------------------------------------------------------------------
--------------------------------------------------------------------------------


-- Module ----------------------------------------------------------------------
--------------------------------------------------------------------------------
-- MAP Extension Data Type.
--------------------------------------------------------------------------------
--------------------------------------------------------------------------------

--not used MAP-ExtensionDataTypes { 
--not used ccitt identified-organization (4) etsi (0) mobileDomain (0) 
--not used gsm-Network (1) modules (3) map-ExtensionDataTypes (21) version3 (3)} 
--not used 
--not used DEFINITIONS 
--not used 
--not used IMPLICIT TAGS 
--not used 
--not used ::= 
--not used 
--not used BEGIN 
--not used 
--not used EXPORTS 
--not used 
--not used PrivateExtension, 
--not used ExtensionContainer; 
--not used 
--not used 
-- IOC for private MAP extensions 
--not used 

--change for compiler 
--change for compiler MAP-EXTENSION ::= CLASS { 
--change for compiler &ExtensionType OPTIONAL, 
--change for compiler &extensionId OBJECT IDENTIFIER }
--change for compiler 
 
-- The length of the Object Identifier shall not exceed 16 octets and the 
-- number of components of the Object Identifier shall not exceed 16 



-- data types 

ExtensionContainer ::= SEQUENCE { 
privateExtensionList [0]PrivateExtensionList OPTIONAL, 
pcs-Extensions [1]PCS-Extensions OPTIONAL, 
 ...} 
 
PrivateExtensionList ::= SEQUENCE SIZE (1..maxNumOfPrivateExtensions) OF 
PrivateExtension 

--change for compiler 
--change for compiler PrivateExtension ::= SEQUENCE { 
--change for compiler extId MAP-EXTENSION.&extensionId 
--change for compiler ({ExtensionSet}), 
--change for compiler extType MAP-EXTENSION.&ExtensionType 
--change for compiler ({ExtensionSet}{@extId}) OPTIONAL} 
--change for compiler 

------------------------------------------------------------
-- Replacement for type PrivateExtension.
------------------------------------------------------------

PrivateExtension ::= SEQUENCE {
     extensionId     OBJECT IDENTIFIER,
     extensionType   ANY OPTIONAL
     }
     
 
 maxNumOfPrivateExtensions INTEGER ::= 10 
 
--not impl 
--not impl ExtensionSet MAP-EXTENSION ::= 
--not impl {... 
-- ExtensionSet is the set of all defined private extensions 
--not impl  } 
--not impl 

-- Unsupported private extensions shall be discarded if received. 



PCS-Extensions ::= SEQUENCE { 
...} 


--not used 
--not used END 
--not used 

--------------------------------------------------------------------------------
--------------------------------------------------------------------------------
-------------------------------------------------------------------------------- 



--------------------------------------------------------------------------------
--------------------------------------------------------------------------------
-- Added global module definition (end).
--------------------------------------------------------------------------------
--------------------------------------------------------------------------------

END

--------------------------------------------------------------------------------
--------------------------------------------------------------------------------
